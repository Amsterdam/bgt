FME workspace aanmaak_esrishape_csv_test_zip.fmw
Title: BGT producten
Description: Frietsnijder shapefiles

Parameters:
- SourceDataset_POSTGIS = bgt_dev_local   # Connection
- DestDataset_ESRISHAPE2 = C:\BGT\FME\esri_shape\gebied.zip   # Destination Esri Shapefolder
- DestDataset_ESRISHAPE3 = C:\BGT\FME\esri_shape\totaalgebied.zip   # Destination Esri Shapefolder
- SourceDataset_POSTGIS_3 = bgt_dev_local   # Connection
- DestDataset_CSV = C:\BGT\FME\wkt\gebieden   # Destination CSV (CommaSeparatedValue) Folder
- DestDataset_CSV_3 = C:\BGT\FME\wkt\totaal   # Destination CSV (CommaSeparatedValue) Folder

Readers:
- POSTGIS_1: POSTGIS from $(SourceDataset_POSTGIS) in EPSG:28992
- POSTGIS_2: POSTGIS from $(SourceDataset_POSTGIS_3) in EPSG:28992

Writers:
- ESRISHAPE_1: ESRISHAPE to $(DestDataset_ESRISHAPE2) in EPSG:28992
- ESRISHAPE_2: ESRISHAPE to $(DestDataset_ESRISHAPE3) in EPSG:28992
- CSV_1: CSV to $(DestDataset_CSV) in EPSG:28992
- CSV_2: CSV to $(DestDataset_CSV_3)

imgeo_extractie.vw_imgeo_straatmeubilair (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_14
Note: Data Flow
AttributeManager_14
    ATTR_TABLE = SET_TO bestandsnaam = FME_CONDITIONAL:DEFAULT_VALUE'_FME_NO_OP_'BOOL_OP;AND;COMPOSITE_TEST;<Unused>;TEST bestandsnaam ATTRIBUTE_VALUE_NULL _FME_BLANK_STRING_'@Value(bestandsnaam_plus)'FME_NUM_CONDITIONS2___
    -> verzamelaar
imgeo_extractie.vw_imgeo_put (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_12
AttributeManager_12
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar
imgeo_extractie.vw_imgeo_mast (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_9
AttributeManager_9
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar
imgeo_extractie.vw_imgeo_kast (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager
AttributeManager
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar
imgeo_extractie.vw_imgeo_installatie (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_8
AttributeManager_8
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar
imgeo_extractie.vw_imgeo_bord (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_5
AttributeManager_5
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar
imgeo_extractie.vw_imgeo_bak (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_4
AttributeManager_4
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar
imgeo_extractie.vw_imgeo_weginrichtingselement (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_20
AttributeManager_20
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_8
GeometryFilter_8
    BREAK_AGG = Yes
    GEOM_PORT_NAMES = Point Line Area Surface
    INSTANTIATE = Yes
    POINT -> AttributeManager_34
    LINE -> AttributeManager_35
    AREA -> AttributeManager_36
    SURFACE -> AttributeManager_36
AttributeManager_34
    ATTR_TABLE = SET_TO bestandsnaam = FME_CONDITIONAL:DEFAULT_VALUE'_FME_NO_OP_'BOOL_OP;OR;COMPOSITE_TEST;<Unused>;TEST @Value(bestandsnaam) IN BGTPLUS_WGI_wegmarkering,BGTPLUS_WGI_wildrooster,BGTPLUS_WGI_rooster,BGTPLUS_WGI_geleideconstructie,BGTPLUS_WGI_boomspiegel,BGTPLUS_WGI_onbekend'@Value(bestandsnaam)_P'FME_NUM_CONDITIONS2___
    -> verzamelaar
AttributeManager_35
    ATTR_TABLE = SET_TO bestandsnaam = FME_CONDITIONAL:DEFAULT_VALUE'_FME_NO_OP_'BOOL_OP;OR;COMPOSITE_TEST;<Unused>;TEST @Value(bestandsnaam) IN BGTPLUS_WGI_wegmarkering,BGTPLUS_WGI_wildrooster,BGTPLUS_WGI_rooster,BGTPLUS_WGI_geleideconstructie,BGTPLUS_WGI_boomspiegel,BGTPLUS_WGI_onbekend'@Value(bestandsnaam)_L'FME_NUM_CONDITIONS2___
    -> verzamelaar_2
AttributeManager_36
    ATTR_TABLE = SET_TO bestandsnaam = FME_CONDITIONAL:DEFAULT_VALUE'_FME_NO_OP_'BOOL_OP;OR;COMPOSITE_TEST;<Unused>;TEST @Value(bestandsnaam) IN BGTPLUS_WGI_wegmarkering,BGTPLUS_WGI_wildrooster,BGTPLUS_WGI_rooster,BGTPLUS_WGI_geleideconstructie,BGTPLUS_WGI_boomspiegel,BGTPLUS_WGI_onbekend'@Value(bestandsnaam)_V'FME_NUM_CONDITIONS2___
    -> verzamelaar_3
imgeo_extractie.vw_imgeo_waterinrichtingselement (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_19
AttributeManager_19
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_3
GeometryFilter_3
    BREAK_AGG = Yes
    GEOM_PORT_NAMES = Point Line
    INSTANTIATE = Yes
    POINT -> AttributeManager_32
    LINE -> AttributeManager_33
AttributeManager_32
    ATTR_TABLE = SET_TO bestandsnaam = FME_CONDITIONAL:DEFAULT_VALUE'_FME_NO_OP_'BOOL_OP;OR;COMPOSITE_TEST;<Unused>;TEST @Value(bestandsnaam) = BGTPLUS_WDI_onbekend'@Value(bestandsnaam)_P'FME_NUM_CONDITIONS2___
    -> verzamelaar
AttributeManager_33
    ATTR_TABLE = SET_TO bestandsnaam = FME_CONDITIONAL:DEFAULT_VALUE'_FME_NO_OP_'BOOL_OP;OR;COMPOSITE_TEST;<Unused>;TEST @Value(bestandsnaam) = BGTPLUS_WDI_onbekend'@Value(bestandsnaam)_L'FME_NUM_CONDITIONS2___
    -> verzamelaar_2
imgeo_extractie.vw_imgeo_vegetatieobject (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_18
AttributeManager_18
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_7
GeometryFilter_7
    BREAK_AGG = Yes
    GEOM_PORT_NAMES = Point Line Area Surface
    INSTANTIATE = Yes
    POINT -> AttributeManager_29
    LINE -> AttributeManager_30
    AREA -> AttributeManager_31
    SURFACE -> AttributeManager_31
AttributeManager_29
    ATTR_TABLE = SET_TO bestandsnaam = FME_CONDITIONAL:DEFAULT_VALUE'_FME_NO_OP_'BOOL_OP;OR;COMPOSITE_TEST;<Unused>;TEST @Value(bestandsnaam) IN BGTPLUS_VGT_haag,BGTPLUS_VGT_onbekend'@Value(bestandsnaam)_P'FME_NUM_CONDITIONS2___
    -> verzamelaar
AttributeManager_30
    ATTR_TABLE = SET_TO bestandsnaam = FME_CONDITIONAL:DEFAULT_VALUE'_FME_NO_OP_'BOOL_OP;OR;COMPOSITE_TEST;<Unused>;TEST @Value(bestandsnaam) IN BGTPLUS_VGT_haag,BGTPLUS_VGT_onbekend'@Value(bestandsnaam)_L'FME_NUM_CONDITIONS2___
    -> verzamelaar_2
AttributeManager_31
    ATTR_TABLE = SET_TO bestandsnaam = FME_CONDITIONAL:DEFAULT_VALUE'_FME_NO_OP_'BOOL_OP;OR;COMPOSITE_TEST;<Unused>;TEST @Value(bestandsnaam) IN BGTPLUS_VGT_haag,BGTPLUS_VGT_onbekend'@Value(bestandsnaam)_V'FME_NUM_CONDITIONS2___
    -> verzamelaar_3
imgeo_extractie.vw_imgeo_sensor (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_17
AttributeManager_17
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_4
GeometryFilter_4
    BREAK_AGG = Yes
    GEOM_PORT_NAMES = Point Line
    INSTANTIATE = Yes
    POINT -> AttributeManager_27
    LINE -> AttributeManager_28
AttributeManager_27
    ATTR_TABLE = SET_TO bestandsnaam = FME_CONDITIONAL:DEFAULT_VALUE'_FME_NO_OP_'BOOL_OP;OR;COMPOSITE_TEST;<Unused>;TEST @Value(bestandsnaam) = BGTPLUS_SSR_onbekend'@Value(bestandsnaam)_P'FME_NUM_CONDITIONS2___
    -> verzamelaar
AttributeManager_28
    ATTR_TABLE = SET_TO bestandsnaam = FME_CONDITIONAL:DEFAULT_VALUE'_FME_NO_OP_'BOOL_OP;OR;COMPOSITE_TEST;<Unused>;TEST @Value(bestandsnaam) = BGTPLUS_SSR_onbekend'@Value(bestandsnaam)_L'FME_NUM_CONDITIONS2___
    -> verzamelaar_2
imgeo_extractie.vw_imgeo_scheiding (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_2
AttributeManager_2
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_5
GeometryFilter_5
    BREAK_AGG = Yes
    GEOM_PORT_NAMES = Line Area Surface
    INSTANTIATE = Yes
    LINE -> AttributeManager_3
    SURFACE -> AttributeManager_24
    AREA -> AttributeManager_24
AttributeManager_3
    ATTR_TABLE = SET_TO bestandsnaam = FME_CONDITIONAL:DEFAULT_VALUE'_FME_NO_OP_'BOOL_OP;OR;COMPOSITE_TEST;<Unused>;TEST @Value(bestandsnaam) IN BGT_SDG_muur,BGT_SDG_kademuur,BGT_SDG_transitie,BGTPLUS_SDG_onbekend'@Value(bestandsnaam)_L'FME_NUM_CONDITIONS2___
    -> verzamelaar_2
AttributeManager_24
    ATTR_TABLE = SET_TO bestandsnaam = FME_CONDITIONAL:DEFAULT_VALUE'_FME_NO_OP_'BOOL_OP;OR;COMPOSITE_TEST;<Unused>;TEST @Value(bestandsnaam) IN BGT_SDG_muur,BGT_SDG_kademuur,BGT_SDG_transitie,BGTPLUS_SDG_onbekend'@Value(bestandsnaam)_V'FME_NUM_CONDITIONS2___
    -> verzamelaar_3
imgeo_extractie.vw_imgeo_overigescheiding (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_16
AttributeManager_16
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_6
GeometryFilter_6
    BREAK_AGG = Yes
    GEOM_PORT_NAMES = Line Area Surface
    INSTANTIATE = Yes
    LINE -> AttributeManager_25
    AREA -> AttributeManager_26
    SURFACE -> AttributeManager_26
AttributeManager_25
    ATTR_TABLE = SET_TO bestandsnaam = FME_CONDITIONAL:DEFAULT_VALUE'_FME_NO_OP_'BOOL_OP;OR;COMPOSITE_TEST;<Unused>;TEST @Value(bestandsnaam) IN BGTPLUS_OSDG_muur,BGTPLUS_OSDG_kademuur,BGTPLUS_OSDG_onbekend'@Value(bestandsnaam)_L'FME_NUM_CONDITIONS2___
    -> verzamelaar_2
AttributeManager_26
    ATTR_TABLE = SET_TO bestandsnaam = FME_CONDITIONAL:DEFAULT_VALUE'_FME_NO_OP_'BOOL_OP;OR;COMPOSITE_TEST;<Unused>;TEST @Value(bestandsnaam) IN BGTPLUS_OSDG_muur,BGTPLUS_OSDG_kademuur,BGTPLUS_OSDG_onbekend'@Value(bestandsnaam)_V'FME_NUM_CONDITIONS2___
    -> verzamelaar_3
imgeo_extractie.vw_imgeo_kunstwerkdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_15
AttributeManager_15
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_9
GeometryFilter_9
    BREAK_AGG = Yes
    GEOM_PORT_NAMES = Point Line Area Surface
    INSTANTIATE = Yes
    LINE -> AttributeManager_21
    POINT -> AttributeManager_22
    AREA -> AttributeManager_23
    SURFACE -> AttributeManager_23
AttributeManager_22
    ATTR_TABLE = SET_TO bestandsnaam = FME_CONDITIONAL:DEFAULT_VALUE'_FME_NO_OP_'BOOL_OP;OR;COMPOSITE_TEST;<Unused>;TEST @Value(bestandsnaam) IN BGT_KDL_hoogspanningsmast,BGT_KDL_transitie, BGT_KDL_onbekend'@Value(bestandsnaam)_P'FME_NUM_CONDITIONS2___
    -> verzamelaar
Note: imgeo objecten: geometrietype punten
verzamelaar: Counter
    SCOPE = Global
    DOMAIN = counter
    CNT_ATTR = _count
    START = 0
    -> SpatialRelator_2 [input 1]
    -> StringConcatenator_19
Note: Shapefiles_totaalgebied
StringConcatenator_19
    ATTRLIST = bestandsnaam
    ACTION = Overwrite Existing Attributes
    PARM_LINE = @Value(bestandsnaam)
    -> Shapefile1 (writer ESRISHAPE_2)
    -> GeometryExtractor_35
Shapefile1 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
AttributeManager_21
    ATTR_TABLE = SET_TO bestandsnaam = FME_CONDITIONAL:DEFAULT_VALUE'_FME_NO_OP_'BOOL_OP;OR;COMPOSITE_TEST;<Unused>;TEST @Value(bestandsnaam) IN BGT_KDL_stuw,BGT_KDL_transitie,BGTPLUS_KDL_duiker,BGTPLUS_KDL_onbekend'@Value(bestandsnaam)_L'FME_NUM_CONDITIONS2___
    -> verzamelaar_2
Note: imgeo objecten: geometrietype lijnen
verzamelaar_2: Counter
    SCOPE = Global
    DOMAIN = counter
    CNT_ATTR = _count
    START = 0
    -> SpatialRelator_4 [input 1]
    -> StringConcatenator_20
StringConcatenator_20
    ATTRLIST = bestandsnaam
    ACTION = Overwrite Existing Attributes
    PARM_LINE = @Value(bestandsnaam)
    -> Shapefile100 (writer ESRISHAPE_2)
    -> GeometryExtractor_36
Shapefile100 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
AttributeManager_23
    ATTR_TABLE = SET_TO bestandsnaam = FME_CONDITIONAL:DEFAULT_VALUE'_FME_NO_OP_'BOOL_OP;OR;COMPOSITE_TEST;<Unused>;TEST @Value(bestandsnaam) IN BGT_KDL_hoogspanningsmast,BGT_KDL_transitie,BGT_KDL_stuw,BGTPLUS_KDL_duiker,BGTPLUS_KDL_onbekend'@Value(bestandsnaam)_V'FME_NUM_CONDITIONS2___
    -> verzamelaar_3
imgeo_extractie.vw_imgeo_overigbouwwerk (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_10
AttributeManager_10
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar_3
imgeo_extractie.vw_imgeo_gebouwinstallatie (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_7
AttributeManager_7
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar_3
Note: imgeo objecten: geometrietype vlakken
verzamelaar_3: Counter
    SCOPE = Global
    DOMAIN = counter
    CNT_ATTR = _count
    START = 0
    -> SpatialRelator_5 [input 1]
    -> StringConcatenator_21
StringConcatenator_21
    ATTRLIST = bestandsnaam
    ACTION = Overwrite Existing Attributes
    PARM_LINE = @Value(bestandsnaam)
    -> Shapefile10000 (writer ESRISHAPE_2)
    -> GeometryExtractor_37
Note: GebiedenRelatieBGTObjecten
Note: shapesbestandsnaam
Shapefile10000 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
imgeo_extractie.vw_imgeo_paal (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_11
AttributeManager_11
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> SpatialRelator_6 [input 1]
    -> StringConcatenator_22
StringConcatenator_22
    ATTRLIST = bestandsnaam
    ACTION = Overwrite Existing Attributes
    PARM_LINE = @Value(bestandsnaam)
    -> Shapefile1000000 (writer ESRISHAPE_2)
    -> GeometryExtractor_18
Shapefile1000000 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
imgeo_extractie.vw_imgeo_functioneelgebied (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text, naam varchar(200)
    -> AttributeManager_6
AttributeManager_6
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> SpatialRelator_7 [input 1]
    -> StringConcatenator_23
StringConcatenator_23
    ATTRLIST = bestandsnaam
    ACTION = Overwrite Existing Attributes
    PARM_LINE = @Value(bestandsnaam)
    -> Shapefile100000000 (writer ESRISHAPE_2)
    -> GeometryExtractor_19
Shapefile100000000 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
imgeo_extractie.vw_bgt_tunneldeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bestandsnaam text
    -> StringConcatenator_24
    -> SpatialRelator_8 [input 1]
StringConcatenator_24
    ATTRLIST = bestandsnaam
    ACTION = Overwrite Existing Attributes
    PARM_LINE = @Value(bestandsnaam)
    -> Shapefile100000001 (writer ESRISHAPE_2)
    -> GeometryExtractor_20
Shapefile100000001 (writer ESRISHAPE_2)
    attributes: namespace char(8), lokaalid char(38), begintijd date, einddtijd date, tijdreg char(20), eindreg char(20), lv_pubdat char(20), bronhoud char(40), inonderzk char(1), hoogtelig short, bgtstatus char(8), plusstatus char(8)
imgeo_extractie.vw_imgeo_spoor (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfunctie varchar(200), bestandsnaam text, plusfunct varchar(200), bestandsnaam_plus text
    -> AttributeManager_13
AttributeManager_13
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> SpatialRelator_3 [input 1]
    -> StringConcatenator_25
StringConcatenator_25
    ATTRLIST = bestandsnaam
    ACTION = Overwrite Existing Attributes
    PARM_LINE = @Value(bestandsnaam)
    -> Shapefile10000000100 (writer ESRISHAPE_2)
    -> GeometryExtractor_21
Shapefile10000000100 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgtfunctie char(200), plusfunct char(200)
imgeo_extractie.vw_bgt_overbruggingsdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), plustype varchar(200), bestandsnaam text, hoortbij varchar(200), isbeweegb varchar(1)
    -> StringConcatenator_26
    -> SpatialRelator_10 [input 1]
StringConcatenator_26
    ATTRLIST = bestandsnaam
    ACTION = Overwrite Existing Attributes
    PARM_LINE = @Value(bestandsnaam)
    -> Shapefile1000000010000 (writer ESRISHAPE_2)
    -> GeometryExtractor_22
Shapefile1000000010000 (writer ESRISHAPE_2)
    attributes: namespace char(8), lokaalid char(38), begintijd date, einddtijd date, tijdreg char(20), eindreg char(20), lv_pubdat char(20), bronhoud char(40), inonderzk char(1), hoogtelig short, bgtstatus char(8), plusstatus char(8), plustype char(200), hoortbij char(200), isbeweegb char(1)
imgeo_extractie.vw_bgt_ongeclassificeerdobject (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bestandsnaam text
    -> StringConcatenator_27
    -> SpatialRelator_11 [input 1]
StringConcatenator_27
    ATTRLIST = bestandsnaam
    ACTION = Overwrite Existing Attributes
    PARM_LINE = @Value(bestandsnaam)
    -> Shapefile100000001000000 (writer ESRISHAPE_2)
    -> GeometryExtractor_23
Shapefile100000001000000 (writer ESRISHAPE_2)
    attributes: namespace char(8), lokaalid char(38), begintijd date, einddtijd date, tijdreg char(20), eindreg char(20), lv_pubdat char(20), bronhoud char(40), inonderzk char(1), hoogtelig short, bgtstatus char(8), plusstatus char(8)
imgeo_extractie.vw_bgt_pand (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bestandsnaam text, bagpndid varchar(20)
    -> StringConcatenator_28
    -> SpatialRelator_12 [input 1]
StringConcatenator_28
    ATTRLIST = bestandsnaam
    ACTION = Overwrite Existing Attributes
    PARM_LINE = @Value(bestandsnaam)
    -> Shapefile10000000100000000 (writer ESRISHAPE_2)
    -> GeometryExtractor_24
Shapefile10000000100000000 (writer ESRISHAPE_2)
    attributes: namespace char(8), lokaalid char(38), begintijd date, einddtijd date, tijdreg char(20), eindreg char(20), lv_pubdat char(20), bronhoud char(40), inonderzk char(1), hoogtelig short, bgtstatus char(8), plusstatus char(8), bagpndid char(20)
imgeo_extractie.vw_bgt_kruinlijn (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), optalud varchar(1), bestandsnaam text, hoortbij varchar(200)
    -> StringConcatenator_29
    -> SpatialRelator_13 [input 1]
StringConcatenator_29
    ATTRLIST = bestandsnaam
    ACTION = Overwrite Existing Attributes
    PARM_LINE = @Value(bestandsnaam)
    -> Shapefile1000000010000000000 (writer ESRISHAPE_2)
    -> GeometryExtractor_25
Shapefile1000000010000000000 (writer ESRISHAPE_2)
    attributes: namespace char(8), lokaalid char(38), begintijd date, einddtijd date, tijdreg char(20), eindreg char(20), lv_pubdat char(20), bronhoud char(40), inonderzk char(1), hoogtelig short, bgtstatus char(8), plusstatus char(8), optalud char(1), hoortbij char(200)
imgeo_extractie.vw_bgt_plaatsbepalingspunt (reader POSTGIS_2) [off]
    attributes: namespace varchar(8), lokaalid varchar(38), nauwkeurig int4, dat_inwinn date, inw_instan varchar(40), inw_methid varchar(40), bestandsnaam text
    -> StringConcatenator_30
    -> SpatialRelator_9 [input 1]
StringConcatenator_30
    ATTRLIST = bestandsnaam
    ACTION = Overwrite Existing Attributes
    PARM_LINE = @Value(bestandsnaam)
    -> Shapefile100000001000000000000 (writer ESRISHAPE_2)
    -> GeometryExtractor_26
Shapefile100000001000000000000 (writer ESRISHAPE_2)
    attributes: namespace char(8), lokaalid char(38), nauwkeurig long, dat_inwinn date, inw_instan char(40), inw_methid char(40)
imgeo_extractie.vw_bgt_openbareruimtelabel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bagoprid varchar(20), oprtype varchar(200), bestandsnaam text, labeltekst varchar(200), hoek float4
    -> StringConcatenator_31
    -> SpatialRelator_14 [input 1]
StringConcatenator_31
    ATTRLIST = bestandsnaam
    ACTION = Overwrite Existing Attributes
    PARM_LINE = @Value(bestandsnaam)
    -> Shapefile10000000100000000000000 (writer ESRISHAPE_2)
    -> GeometryExtractor_27
Shapefile10000000100000000000000 (writer ESRISHAPE_2)
    attributes: namespace char(8), lokaalid char(38), begintijd date, einddtijd date, tijdreg char(20), eindreg char(20), lv_pubdat char(20), bronhoud char(40), inonderzk char(1), hoogtelig short, bgtstatus char(8), plusstatus char(8), bagoprid char(20), oprtype char(200), labeltekst char(200), hoek float
imgeo_extractie.vw_bgt_nummeraanduidingreeks (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bestandsnaam text, bagpndid varchar(20), bagvbolgst varchar(20), bagvbohgst varchar(20), labeltekst varchar(200), hoek float4
    -> StringConcatenator_32
    -> SpatialRelator_15 [input 1]
StringConcatenator_32
    ATTRLIST = bestandsnaam
    ACTION = Overwrite Existing Attributes
    PARM_LINE = @Value(bestandsnaam)
    -> Shapefile1000000010000000000000000 (writer ESRISHAPE_2)
    -> GeometryExtractor_28
Shapefile1000000010000000000000000 (writer ESRISHAPE_2)
    attributes: namespace char(8), lokaalid char(38), begintijd date, einddtijd date, tijdreg char(20), eindreg char(20), lv_pubdat char(20), bronhoud char(40), inonderzk char(1), hoogtelig short, bgtstatus char(8), plusstatus char(8), bagpndid char(20), bagvbolgst char(20), bagvbohgst char(20), labeltekst char(200), hoek float
imgeo_extractie.vw_bgt_ondersteunendwegdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfunctie varchar(200), bestandsnaam text, bgtfysvkn varchar(200), optalud varchar(1), plusfunct varchar(200), plusfysvkn varchar(200)
    -> StringConcatenator_33
    -> SpatialRelator [input 1]
StringConcatenator_33
    ATTRLIST = bestandsnaam
    ACTION = Overwrite Existing Attributes
    PARM_LINE = @Value(bestandsnaam)
    -> Shapefile100000001000000000000000000 (writer ESRISHAPE_2)
    -> GeometryExtractor_29
Shapefile100000001000000000000000000 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgtfunctie char(200), bgtfysvkn char(200), optalud char(1), plusfunct char(200), plusfysvkn char(200)
imgeo_extractie.vw_bgt_wegdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfunctie varchar(200), bestandsnaam text, bgtfysvkn varchar(200), optalud varchar(1), plusfunct varchar(200), plusfysvkn varchar(200)
    -> StringConcatenator_34
    -> SpatialRelator [input 1]
StringConcatenator_34
    ATTRLIST = bestandsnaam
    ACTION = Overwrite Existing Attributes
    PARM_LINE = @Value(bestandsnaam)
    -> Shapefile10000000100000000000000000000 (writer ESRISHAPE_2)
    -> GeometryExtractor_30
Shapefile10000000100000000000000000000 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgtfunctie char(200), bgtfysvkn char(200), optalud char(1), plusfunct char(200), plusfysvkn char(200)
imgeo_extractie.vw_bgt_begroeidterreindeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfysvkn varchar(200), bestandsnaam text, optalud varchar(1), plusfysvkn varchar(200)
    -> StringConcatenator_35
    -> SpatialRelator_16 [input 1]
StringConcatenator_35
    ATTRLIST = bestandsnaam
    ACTION = Overwrite Existing Attributes
    PARM_LINE = @Value(bestandsnaam)
    -> Shapefile1000000010000000000000000000000 (writer ESRISHAPE_2)
    -> GeometryExtractor_31
Shapefile1000000010000000000000000000000 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgtfysvkn char(200), optalud char(1), plusfysvkn char(200)
imgeo_extractie.vw_bgt_onbegroeidterreindeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfysvkn varchar(200), bestandsnaam text, optalud varchar(1), plusfysvkn varchar(200)
    -> StringConcatenator_36
    -> SpatialRelator_16 [input 1]
StringConcatenator_36
    ATTRLIST = bestandsnaam
    ACTION = Overwrite Existing Attributes
    PARM_LINE = @Value(bestandsnaam)
    -> Shapefile1000000010000000000000000000001 (writer ESRISHAPE_2)
    -> GeometryExtractor_32
Shapefile1000000010000000000000000000001 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgtfysvkn char(200), optalud char(1), plusfysvkn char(200)
imgeo_extractie.vw_bgt_ondersteunendwaterdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200)
    -> StringConcatenator_37
    -> SpatialRelator_17 [input 1]
StringConcatenator_37
    ATTRLIST = bestandsnaam
    ACTION = Overwrite Existing Attributes
    PARM_LINE = @Value(bestandsnaam)
    -> Shapefile100000001000000000000000000000100 (writer ESRISHAPE_2)
    -> GeometryExtractor_33
Shapefile100000001000000000000000000000100 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
imgeo_extractie.vw_bgt_waterdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), bgttype varchar(200), bestandsnaam text, plusstatus varchar(8)
    -> StringConcatenator_38
    -> SpatialRelator_17 [input 1]
StringConcatenator_38
    ATTRLIST = bestandsnaam
    ACTION = Overwrite Existing Attributes
    PARM_LINE = @Value(bestandsnaam)
    -> Shapefile10000000100000000000000000000010000 (writer ESRISHAPE_2)
    -> GeometryExtractor_34
Shapefile10000000100000000000000000000010000 (writer ESRISHAPE_2)
    attributes: namespace char(8), lokaalid char(38), begintijd date, einddtijd date, tijdreg char(20), eindreg char(20), lv_pubdat char(20), bronhoud char(40), inonderzk char(1), hoogtelig short, bgtstatus char(8), bgttype char(200), plusstatus char(8)
imgeo.pdt_kaartblad (reader POSTGIS_1)
    attributes: id serial,PRIKEY, naam varchar(200), big_id int4
    -> AttributeFilter
Note: kaartbladen
AttributeFilter
    ATTR_NAME = big_id
    ATTR_VALUES = <EMPTY>,<MISSING>,<NULL>,<UNFILTERED>,2
    2 -> SpikeRemover_2
SpikeRemover_2
    SPIKEANGLE = 0.0001
    UNCHANGED -> SliverRemover_3
    CHANGED -> SliverRemover_3
SliverRemover_3
    REPAIR_METHOD = Longest Boundary
    REPAIRED -> SpatialRelator_2 [input 2]
    REPAIRED -> SpatialRelator_4 [input 2]
    REPAIRED -> SpatialRelator_5 [input 2]
    REPAIRED -> SpatialRelator_3 [input 2]
    REPAIRED -> SpatialRelator_6 [input 2]
    REPAIRED -> SpatialRelator_7 [input 2]
    REPAIRED -> SpatialRelator_8 [input 2]
    REPAIRED -> SpatialRelator_9 [input 2]
    REPAIRED -> SpatialRelator_10 [input 2]
    REPAIRED -> SpatialRelator_11 [input 2]
    REPAIRED -> SpatialRelator_12 [input 2]
    REPAIRED -> SpatialRelator_13 [input 2]
    REPAIRED -> SpatialRelator_14 [input 2]
    REPAIRED -> SpatialRelator_15 [input 2]
    REPAIRED -> SpatialRelator_16 [input 2]
    REPAIRED -> SpatialRelator_17 [input 2]
    REPAIRED -> SpatialRelator [input 2]
Note: Shapefilrs per gebied
Note: Punten
imgeo_extractie.vw_imgeo_kunstwerkdeel_point (writer ESRISHAPE_1)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
Note: Lijnen
imgeo_extractie.vw_imgeo_kunstwerkdeel_line (writer ESRISHAPE_1)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
Note: Vlakken
imgeo_extractie.vw_imgeo_kunstwerkdeel_polygon (writer ESRISHAPE_1)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
GeometryExtractor_4
    REMOVE_GEOMETRY = No
    ATTR = geometry
    OGC_WKT_PRECISION_DISPLAY = Shortened 64-bit
    KIND_LONG = OGC Well Known Text
    OGCVERSION = 1.1
    -> AttributeManager_40
imgeo_extractie.vw_imgeo_spoor00 (writer ESRISHAPE_1)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
GeometryExtractor_5
    REMOVE_GEOMETRY = No
    ATTR = geometry
    OGC_WKT_PRECISION_DISPLAY = Shortened 64-bit
    KIND_LONG = OGC Well Known Text
    OGCVERSION = 1.1
    -> AttributeManager_41
imgeo_extractie.vw_imgeo_spoor0000 (writer ESRISHAPE_1)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
Shapefile1010000 (writer ESRISHAPE_1)
    attributes: namespace char(8), lokaalid char(38), begintijd date, einddtijd date, tijdreg char(20), eindreg char(20), lv_pubdat char(20), bronhoud char(40), inonderzk char(1), hoogtelig short, bgtstatus char(8), plusstatus char(8)
Shapefile101000000 (writer ESRISHAPE_1)
    attributes: namespace char(8), lokaalid char(38), begintijd date, einddtijd date, tijdreg char(20), eindreg char(20), lv_pubdat char(20), bronhoud char(40), inonderzk char(1), hoogtelig short, bgtstatus char(8), plusstatus char(8), bgtfunctie char(200), plusfunct char(200)
Shapefile1010001 (writer ESRISHAPE_1)
    attributes: namespace char(8), lokaalid char(38), begintijd date, einddtijd date, tijdreg char(20), eindreg char(20), lv_pubdat char(20), bronhoud char(40), inonderzk char(1), hoogtelig short, bgtstatus char(8), plusstatus char(8), plustype char(200), hoortbij char(200), isbeweegb char(1)
Shapefile1010002 (writer ESRISHAPE_1)
    attributes: namespace char(8), lokaalid char(38), begintijd date, einddtijd date, tijdreg char(20), eindreg char(20), lv_pubdat char(20), bronhoud char(40), inonderzk char(1), hoogtelig short, bgtstatus char(8), plusstatus char(8)
Shapefile1010003 (writer ESRISHAPE_1)
    attributes: namespace char(8), lokaalid char(38), begintijd date, einddtijd date, tijdreg char(20), eindreg char(20), lv_pubdat char(20), bronhoud char(40), inonderzk char(1), hoogtelig short, bgtstatus char(8), plusstatus char(8), bagpndid char(20)
Shapefile101000300 (writer ESRISHAPE_1)
    attributes: namespace char(8), lokaalid char(38), begintijd date, einddtijd date, tijdreg char(20), eindreg char(20), lv_pubdat char(20), bronhoud char(40), inonderzk char(1), hoogtelig short, bgtstatus char(8), plusstatus char(8), optalud char(1), hoortbij char(200)
imgeo_extractie.vw_imgeo_spoor00000000 (writer ESRISHAPE_1) [off]
    attributes: namespace char(8), lokaalid char(38), nauwkeurig long, dat_inwinn date, inw_instan char(40), inw_methid char(40)
Shapefile10100 (writer ESRISHAPE_1)
    attributes: namespace char(8), lokaalid char(38), begintijd date, einddtijd date, tijdreg char(20), eindreg char(20), lv_pubdat char(20), bronhoud char(40), inonderzk char(1), hoogtelig short, bgtstatus char(8), plusstatus char(8), bagoprid char(20), oprtype char(200), labeltekst char(200), hoek float
Shapefile101 (writer ESRISHAPE_1)
    attributes: namespace char(8), lokaalid char(38), begintijd date, einddtijd date, tijdreg char(20), eindreg char(20), lv_pubdat char(20), bronhoud char(40), inonderzk char(1), hoogtelig short, bgtstatus char(8), plusstatus char(8), bagpndid char(20), bagvbolgst char(20), bagvbohgst char(20), labeltekst char(200), hoek float
Shapefile1 (writer ESRISHAPE_1)
    attributes: namespace char(8), lokaalid char(38), begintijd date, einddtijd date, tijdreg char(20), eindreg char(20), lv_pubdat char(20), bronhoud char(40), inonderzk char(1), hoogtelig short, bgtstatus char(8), plusstatus char(8), bgtfunctie char(200), bgtfysvkn char(200), optalud char(1), plusfunct char(200), plusfysvkn char(200)
Shapefile100 (writer ESRISHAPE_1)
    attributes: namespace char(8), lokaalid char(38), begintijd date, einddtijd date, tijdreg char(20), eindreg char(20), lv_pubdat char(20), bronhoud char(40), inonderzk char(1), hoogtelig short, bgtstatus char(8), plusstatus char(8), bgtfysvkn char(200), optalud char(1), plusfysvkn char(200)
Shapefile10000 (writer ESRISHAPE_1)
    attributes: namespace char(8), lokaalid char(38), begintijd date, einddtijd date, tijdreg char(20), eindreg char(20), lv_pubdat char(20), bronhoud char(40), inonderzk char(1), hoogtelig short, bgtstatus char(8), bgttype char(200), plusstatus char(8), plustype char(200)

Bookmark: CSV Totaal gebied
GeometryExtractor_35
    REMOVE_GEOMETRY = No
    ATTR = geometry
    OGC_WKT_PRECISION_DISPLAY = Shortened 64-bit
    KIND_LONG = OGC Well Known Text
    OGCVERSION = 1.1
    -> AttributeManager_71
AttributeManager_71
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
    -> imgeo_extractie.vw_bgt_waterdeel01 (writer CSV_2)
imgeo_extractie.vw_bgt_waterdeel01 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-type char(8), plus-type char(200), geometry float
GeometryExtractor_36
    REMOVE_GEOMETRY = No
    ATTR = geometry
    OGC_WKT_PRECISION_DISPLAY = Shortened 64-bit
    KIND_LONG = OGC Well Known Text
    OGCVERSION = 1.1
    -> AttributeManager_72
AttributeManager_72
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
    -> imgeo_extractie.vw_bgt_waterdeel02 (writer CSV_2)
imgeo_extractie.vw_bgt_waterdeel02 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-type char(8), plus-type char(200), geometry float
GeometryExtractor_37
    REMOVE_GEOMETRY = No
    ATTR = geometry
    OGC_WKT_PRECISION_DISPLAY = Shortened 64-bit
    KIND_LONG = OGC Well Known Text
    OGCVERSION = 1.1
    -> AttributeManager_73
AttributeManager_73
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
    -> imgeo_extractie.vw_bgt_waterdeel03 (writer CSV_2)
imgeo_extractie.vw_bgt_waterdeel03 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-type char(8), plus-type char(200), geometry float

Bookmark: CSV Totaalgebied
GeometryExtractor_18
    REMOVE_GEOMETRY = No
    ATTR = geometry
    OGC_WKT_PRECISION_DISPLAY = Shortened 64-bit
    KIND_LONG = OGC Well Known Text
    OGCVERSION = 1.1
    -> AttributeManager_54
AttributeManager_54
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
    -> imgeo_extractie.vw_bgt_waterdeel (writer CSV_2)
imgeo_extractie.vw_bgt_waterdeel (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), bgt-type char(8), plus-status char(8), plus-type char(200), geometry float
GeometryExtractor_19
    REMOVE_GEOMETRY = No
    ATTR = geometry
    OGC_WKT_PRECISION_DISPLAY = Shortened 64-bit
    KIND_LONG = OGC Well Known Text
    OGCVERSION = 1.1
    -> AttributeManager_55
AttributeManager_55
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
    -> imgeo_extractie.vw_bgt_waterdeel00 (writer CSV_2)
imgeo_extractie.vw_bgt_waterdeel00 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), bgt-type char(8), plus-status char(8), plus-type char(200), geometry float
GeometryExtractor_20
    REMOVE_GEOMETRY = No
    ATTR = geometry
    OGC_WKT_PRECISION_DISPLAY = Shortened 64-bit
    KIND_LONG = OGC Well Known Text
    OGCVERSION = 1.1
    -> AttributeManager_56
AttributeManager_56
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
    -> imgeo_extractie.vw_bgt_waterdeel0000 (writer CSV_2)
imgeo_extractie.vw_bgt_waterdeel0000 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), geometry float
GeometryExtractor_21
    REMOVE_GEOMETRY = No
    ATTR = geometry
    OGC_WKT_PRECISION_DISPLAY = Shortened 64-bit
    KIND_LONG = OGC Well Known Text
    OGCVERSION = 1.1
    -> AttributeManager_57
AttributeManager_57
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfunctie > bgt-functie
      RENAME_SET_VALUE plusfunct > plus-functie
    -> imgeo_extractie.vw_bgt_waterdeel0001 (writer CSV_2)
imgeo_extractie.vw_bgt_waterdeel0001 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-functie char(200), plus-functie char(200), geometry float
GeometryExtractor_22
    REMOVE_GEOMETRY = No
    ATTR = geometry
    OGC_WKT_PRECISION_DISPLAY = Shortened 64-bit
    KIND_LONG = OGC Well Known Text
    OGCVERSION = 1.1
    -> AttributeManager_58
AttributeManager_58
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE plustype > plus-type
      RENAME_SET_VALUE hoortbij > hoortbijtypeoverbrugging
      RENAME_SET_VALUE isbeweegb > overbruggingisbeweegbaar
    -> imgeo_extractie.vw_bgt_waterdeel0002 (writer CSV_2)
imgeo_extractie.vw_bgt_waterdeel0002 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), plus-type char(200), hoortbijtypeoverbrugging char(200), overbruggingisbeweegbaar char(1), geometry float
GeometryExtractor_23
    REMOVE_GEOMETRY = No
    ATTR = geometry
    OGC_WKT_PRECISION_DISPLAY = Shortened 64-bit
    KIND_LONG = OGC Well Known Text
    OGCVERSION = 1.1
    -> AttributeManager_59
AttributeManager_59
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
    -> imgeo_extractie.vw_bgt_waterdeel0003 (writer CSV_2)
imgeo_extractie.vw_bgt_waterdeel0003 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), geometry float
GeometryExtractor_24
    REMOVE_GEOMETRY = No
    ATTR = geometry
    OGC_WKT_PRECISION_DISPLAY = Shortened 64-bit
    KIND_LONG = OGC Well Known Text
    OGCVERSION = 1.1
    -> AttributeManager_60
AttributeManager_60
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bagpndid > identificatiebagpnd
    -> imgeo_extractie.vw_bgt_waterdeel0004 (writer CSV_2)
imgeo_extractie.vw_bgt_waterdeel0004 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), identificatiebagpnd char(20), geometry float
GeometryExtractor_25
    REMOVE_GEOMETRY = No
    ATTR = geometry
    OGC_WKT_PRECISION_DISPLAY = Shortened 64-bit
    KIND_LONG = OGC Well Known Text
    OGCVERSION = 1.1
    -> AttributeManager_61
AttributeManager_61
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
    -> imgeo_extractie.vw_bgt_waterdeel0005 (writer CSV_2)
imgeo_extractie.vw_bgt_waterdeel0005 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), optalud char(1), hoortbijtypeoverbrugging char(200), geometry float
GeometryExtractor_26
    REMOVE_GEOMETRY = No
    ATTR = geometry
    OGC_WKT_PRECISION_DISPLAY = Shortened 64-bit
    KIND_LONG = OGC Well Known Text
    OGCVERSION = 1.1
    -> AttributeManager_62
AttributeManager_62
    ATTR_TABLE:
      RENAME_SET_VALUE namespace > identificatie_namespace
      RENAME_SET_VALUE lokaalid > identificatie_lokaalid
    -> imgeo_extractie.vw_bgt_waterdeel0006 (writer CSV_2)
imgeo_extractie.vw_bgt_waterdeel0006 (writer CSV_2) [off]
    attributes: identificatie_namespace char(8), identificatie_lokaalid char(38), nauwkeurig int, dat_inwinn auto, inw_instan char(40), inw_methid char(40), geometry float
GeometryExtractor_27
    REMOVE_GEOMETRY = No
    ATTR = geometry
    OGC_WKT_PRECISION_DISPLAY = Shortened 64-bit
    KIND_LONG = OGC Well Known Text
    OGCVERSION = 1.1
    -> AttributeManager_63
AttributeManager_63
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bagoprid > identificatieBAGOPR
      RENAME_SET_VALUE oprtype > openbareruimtetype
      RENAME_SET_VALUE labeltekst > label_tekst
    -> imgeo_extractie.vw_bgt_waterdeel0007 (writer CSV_2)
imgeo_extractie.vw_bgt_waterdeel0007 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), identificatieBAGOPR char(20), openbareruimtetype char(200), label_tekst char(200), hoek float, geometry float
GeometryExtractor_28
    REMOVE_GEOMETRY = No
    ATTR = geometry
    OGC_WKT_PRECISION_DISPLAY = Shortened 64-bit
    KIND_LONG = OGC Well Known Text
    OGCVERSION = 1.1
    -> AttributeManager_64
AttributeManager_64
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bagpndid > identificatiebagpnd
      RENAME_SET_VALUE bagvbolgst > id_bagvbolaagste_huisnummer
      RENAME_SET_VALUE bagvbohgst > id_bagvbohoogste_huisnummer
      RENAME_SET_VALUE labeltekst > label_tekst
    -> imgeo_extractie.vw_bgt_waterdeel0008 (writer CSV_2)
imgeo_extractie.vw_bgt_waterdeel0008 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), identificatiebagpnd char(20), id_bagvbolaagste_huisnummer char(20), id_bagvbohoogste_huisnummer char(20), label_tekst char(200), hoek float, geometry float
GeometryExtractor_29
    REMOVE_GEOMETRY = No
    ATTR = geometry
    OGC_WKT_PRECISION_DISPLAY = Shortened 64-bit
    KIND_LONG = OGC Well Known Text
    OGCVERSION = 1.1
    -> AttributeManager_65
AttributeManager_65
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfunctie > bgt-functie
      RENAME_SET_VALUE bgtfysvkn > bgt-fysiekvoorkomen
      RENAME_SET_VALUE plusfunct > plus-functie
      RENAME_SET_VALUE plusfysvkn > plus-fysiekvoorkomen
    -> imgeo_extractie.vw_bgt_waterdeel0009 (writer CSV_2)
imgeo_extractie.vw_bgt_waterdeel0009 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-functie char(200), bgt-fysiekvoorkomen char(200), optalud char(1), plus-functie char(200), plus-fysiekvoorkomen char(200), geometry float
GeometryExtractor_30
    REMOVE_GEOMETRY = No
    ATTR = geometry
    OGC_WKT_PRECISION_DISPLAY = Shortened 64-bit
    KIND_LONG = OGC Well Known Text
    OGCVERSION = 1.1
    -> AttributeManager_66
AttributeManager_66
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfunctie > bgt-functie
      RENAME_SET_VALUE bgtfysvkn > bgt-fysiekvoorkomen
      RENAME_SET_VALUE plusfunct > plus-functie
      RENAME_SET_VALUE plusfysvkn > plus-fysiekvoorkomen
    -> imgeo_extractie.vw_bgt_waterdeel000900 (writer CSV_2)
imgeo_extractie.vw_bgt_waterdeel000900 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-functie char(200), bgt-fysiekvoorkomen char(200), optalud char(1), plus-functie char(200), plus-fysiekvoorkomen char(200), geometry float
GeometryExtractor_31
    REMOVE_GEOMETRY = No
    ATTR = geometry
    OGC_WKT_PRECISION_DISPLAY = Shortened 64-bit
    KIND_LONG = OGC Well Known Text
    OGCVERSION = 1.1
    -> AttributeManager_67
AttributeManager_67
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfysvkn > bgt-fysiekvoorkomen
      RENAME_SET_VALUE plusfysvkn > plus-fysiekvoorkomen
    -> imgeo_extractie.vw_bgt_waterdeel00090000 (writer CSV_2)
imgeo_extractie.vw_bgt_waterdeel00090000 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-fysiekvoorkomen char(200), optalud char(1), plus-fysiekvoorkomen char(200), geometry float
GeometryExtractor_32
    REMOVE_GEOMETRY = No
    ATTR = geometry
    OGC_WKT_PRECISION_DISPLAY = Shortened 64-bit
    KIND_LONG = OGC Well Known Text
    OGCVERSION = 1.1
    -> AttributeManager_68
AttributeManager_68
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfysvkn > bgt-fysiekvoorkomen
      RENAME_SET_VALUE plusfysvkn > plus-fysiekvoorkomen
    -> imgeo_extractie.vw_bgt_waterdeel0009000000 (writer CSV_2)
imgeo_extractie.vw_bgt_waterdeel0009000000 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-fysiekvoorkomen char(200), optalud char(1), plus-fysiekvoorkomen char(200), geometry float
GeometryExtractor_33
    REMOVE_GEOMETRY = No
    ATTR = geometry
    OGC_WKT_PRECISION_DISPLAY = Shortened 64-bit
    KIND_LONG = OGC Well Known Text
    OGCVERSION = 1.1
    -> AttributeManager_69
AttributeManager_69
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
    -> imgeo_extractie.vw_bgt_waterdeel0013 (writer CSV_2)
imgeo_extractie.vw_bgt_waterdeel0013 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-type char(200), plus-type char(200), geometry float
GeometryExtractor_34
    REMOVE_GEOMETRY = No
    ATTR = geometry
    OGC_WKT_PRECISION_DISPLAY = Shortened 64-bit
    KIND_LONG = OGC Well Known Text
    OGCVERSION = 1.1
    -> AttributeManager_70
AttributeManager_70
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
    -> imgeo_extractie.vw_bgt_waterdeel0014 (writer CSV_2)
imgeo_extractie.vw_bgt_waterdeel0014 (writer CSV_2)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), bgt-type char(200), geometry float

Bookmark: GebiedenRelatieBGT_Objecten
SpatialRelator_2
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_2
ListExploder_2
    ATTR_ACCUM_MODE = Merge Incoming List
    ATTR_CONFLICT_RES = Use Incoming List
    INDEX_ATTR = _element_index
    LIST_ATTR = _relationships{}
    ELEMENTS -> StringConcatenator_2
SpatialRelator_4
    SUCCESS_ATTR = _related_candidates
    CALC_CARD = No
    PREDICATES = INTERSECTS CONTAINS
    LIST_NAME = _relationships
    CURVE_BOUNDARY_RULE_PARAM = Default Rule
    AGGREGATE_HANDLING = Yes
    -> ListExploder_4
ListExploder_4
    ATTR_ACCUM_MODE = Merge Incoming List
    ATTR_CONFLICT_RES = Use Incoming List
    INDEX_ATTR = _element_index
    LIST_ATTR = _relationships{}
    ELEMENTS -> StringConcatenator_5
SpatialRelator_5
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_5
ListExploder_5
    ATTR_ACCUM_MODE = Merge Incoming List
    ATTR_CONFLICT_RES = Use Incoming List
    INDEX_ATTR = _element_index
    LIST_ATTR = _relationships{}
    ELEMENTS -> StringConcatenator_6
SpatialRelator_6
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_6
ListExploder_6
    ATTR_ACCUM_MODE = Merge Incoming List
    ATTR_CONFLICT_RES = Use Incoming List
    INDEX_ATTR = _element_index
    LIST_ATTR = _relationships{}
    ELEMENTS -> StringConcatenator_7
SpatialRelator_7
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_7
ListExploder_7
    ATTR_ACCUM_MODE = Merge Incoming List
    ATTR_CONFLICT_RES = Use Incoming List
    INDEX_ATTR = _element_index
    LIST_ATTR = _relationships{}
    ELEMENTS -> StringConcatenator_8
SpatialRelator_8
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_8
ListExploder_8
    ATTR_ACCUM_MODE = Merge Incoming List
    ATTR_CONFLICT_RES = Use Incoming List
    INDEX_ATTR = _element_index
    LIST_ATTR = _relationships{}
    ELEMENTS -> StringConcatenator_9
SpatialRelator_3
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_3
ListExploder_3
    ATTR_ACCUM_MODE = Merge Incoming List
    ATTR_CONFLICT_RES = Use Incoming List
    INDEX_ATTR = _element_index
    LIST_ATTR = _relationships{}
    ELEMENTS -> StringConcatenator_3
SpatialRelator_10
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_10
ListExploder_10
    ATTR_ACCUM_MODE = Merge Incoming List
    ATTR_CONFLICT_RES = Use Incoming List
    INDEX_ATTR = _element_index
    LIST_ATTR = _relationships{}
    ELEMENTS -> StringConcatenator_11
SpatialRelator_11
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_11
ListExploder_11
    ATTR_ACCUM_MODE = Merge Incoming List
    ATTR_CONFLICT_RES = Use Incoming List
    INDEX_ATTR = _element_index
    LIST_ATTR = _relationships{}
    ELEMENTS -> StringConcatenator_12
SpatialRelator_12
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_12
ListExploder_12
    ATTR_ACCUM_MODE = Merge Incoming List
    ATTR_CONFLICT_RES = Use Incoming List
    INDEX_ATTR = _element_index
    LIST_ATTR = _relationships{}
    ELEMENTS -> StringConcatenator_13
SpatialRelator_13
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_13
ListExploder_13
    ATTR_ACCUM_MODE = Merge Incoming List
    ATTR_CONFLICT_RES = Use Incoming List
    INDEX_ATTR = _element_index
    LIST_ATTR = _relationships{}
    ELEMENTS -> StringConcatenator_14
SpatialRelator_9
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_9
ListExploder_9
    ATTR_ACCUM_MODE = Merge Incoming List
    ATTR_CONFLICT_RES = Use Incoming List
    INDEX_ATTR = _element_index
    LIST_ATTR = _relationships{}
    ELEMENTS -> StringConcatenator_10
SpatialRelator_14
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_14
ListExploder_14
    ATTR_ACCUM_MODE = Merge Incoming List
    ATTR_CONFLICT_RES = Use Incoming List
    INDEX_ATTR = _element_index
    LIST_ATTR = _relationships{}
    ELEMENTS -> StringConcatenator_15
SpatialRelator_15
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_15
ListExploder_15
    ATTR_ACCUM_MODE = Merge Incoming List
    ATTR_CONFLICT_RES = Use Incoming List
    INDEX_ATTR = _element_index
    LIST_ATTR = _relationships{}
    ELEMENTS -> StringConcatenator_16
SpatialRelator
    SUCCESS_ATTR = _related_candidates
    CALC_CARD = No
    PREDICATES = CONTAINS INTERSECTS
    LIST_NAME = _relationships
    CURVE_BOUNDARY_RULE_PARAM = Default Rule
    AGGREGATE_HANDLING = Yes
    -> ListExploder
ListExploder
    ATTR_ACCUM_MODE = Merge Incoming List
    ATTR_CONFLICT_RES = Use Incoming List
    INDEX_ATTR = _element_index
    LIST_ATTR = _relationships{}
    ELEMENTS -> StringConcatenator_4
SpatialRelator_16
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_16
ListExploder_16
    ATTR_ACCUM_MODE = Merge Incoming List
    ATTR_CONFLICT_RES = Use Incoming List
    INDEX_ATTR = _element_index
    LIST_ATTR = _relationships{}
    ELEMENTS -> StringConcatenator_17
SpatialRelator_17
    SUCCESS_ATTR = _related_candidates
    CALC_CARD = No
    PREDICATES = CONTAINS INTERSECTS
    LIST_NAME = _relationships
    CURVE_BOUNDARY_RULE_PARAM = Default Rule
    AGGREGATE_HANDLING = Yes
    -> ListExploder_17
ListExploder_17
    ATTR_ACCUM_MODE = Merge Incoming List
    ATTR_CONFLICT_RES = Use Incoming List
    INDEX_ATTR = _element_index
    LIST_ATTR = _relationships{}
    ELEMENTS -> StringConcatenator_18

Bookmark: Bestandsnaam shapefiles
StringConcatenator_2
    ATTRLIST = bestandsnaam
    ACTION = Overwrite Existing Attributes
    PARM_LINE = @Value(bestandsnaam)
    -> imgeo_extractie.vw_imgeo_kunstwerkdeel_point (writer ESRISHAPE_1)
    -> GeometryExtractor
StringConcatenator_5
    ATTRLIST = bestandsnaam
    ACTION = Overwrite Existing Attributes
    PARM_LINE = @Value(bestandsnaam)
    -> imgeo_extractie.vw_imgeo_kunstwerkdeel_line (writer ESRISHAPE_1)
    -> GeometryExtractor_2
StringConcatenator_6
    ATTRLIST = bestandsnaam
    ACTION = Overwrite Existing Attributes
    PARM_LINE = @Value(bestandsnaam)
    -> imgeo_extractie.vw_imgeo_kunstwerkdeel_polygon (writer ESRISHAPE_1)
    -> GeometryExtractor_3
StringConcatenator_7
    ATTRLIST = bestandsnaam
    ACTION = Overwrite Existing Attributes
    PARM_LINE = @Value(bestandsnaam)
    -> imgeo_extractie.vw_imgeo_spoor00 (writer ESRISHAPE_1)
    -> GeometryExtractor_4
StringConcatenator_8
    ATTRLIST = bestandsnaam
    ACTION = Overwrite Existing Attributes
    PARM_LINE = @Value(bestandsnaam)
    -> imgeo_extractie.vw_imgeo_spoor0000 (writer ESRISHAPE_1)
    -> GeometryExtractor_5
StringConcatenator_9
    ATTRLIST = bestandsnaam
    ACTION = Overwrite Existing Attributes
    PARM_LINE = @Value(bestandsnaam)
    -> Shapefile1010000 (writer ESRISHAPE_1)
    -> GeometryExtractor_6
StringConcatenator_3
    ATTRLIST = bestandsnaam
    ACTION = Overwrite Existing Attributes
    PARM_LINE = @Value(bestandsnaam)
    -> Shapefile101000000 (writer ESRISHAPE_1)
    -> GeometryExtractor_7
StringConcatenator_11
    ATTRLIST = bestandsnaam
    ACTION = Overwrite Existing Attributes
    PARM_LINE = @Value(bestandsnaam)
    -> Shapefile1010001 (writer ESRISHAPE_1)
    -> GeometryExtractor_8
StringConcatenator_12
    ATTRLIST = bestandsnaam
    ACTION = Overwrite Existing Attributes
    PARM_LINE = @Value(bestandsnaam)
    -> Shapefile1010002 (writer ESRISHAPE_1)
    -> GeometryExtractor_9
StringConcatenator_13
    ATTRLIST = bestandsnaam
    ACTION = Overwrite Existing Attributes
    PARM_LINE = @Value(bestandsnaam)
    -> Shapefile1010003 (writer ESRISHAPE_1)
    -> GeometryExtractor_10
StringConcatenator_14
    ATTRLIST = bestandsnaam
    ACTION = Overwrite Existing Attributes
    PARM_LINE = @Value(bestandsnaam)
    -> Shapefile101000300 (writer ESRISHAPE_1)
    -> GeometryExtractor_11
StringConcatenator_10
    ATTRLIST = bestandsnaam
    ACTION = Overwrite Existing Attributes
    PARM_LINE = @Value(bestandsnaam)
    -> imgeo_extractie.vw_imgeo_spoor00000000 (writer ESRISHAPE_1)
    -> GeometryExtractor_12
StringConcatenator_15
    ATTRLIST = bestandsnaam
    ACTION = Overwrite Existing Attributes
    PARM_LINE = @Value(bestandsnaam)
    -> Shapefile10100 (writer ESRISHAPE_1)
    -> GeometryExtractor_13
StringConcatenator_16
    ATTRLIST = bestandsnaam
    ACTION = Overwrite Existing Attributes
    PARM_LINE = @Value(bestandsnaam)
    -> Shapefile101 (writer ESRISHAPE_1)
    -> GeometryExtractor_14
StringConcatenator_4
    ATTRLIST = bestandsnaam
    ACTION = Overwrite Existing Attributes
    PARM_LINE = @Value(bestandsnaam)
    -> Shapefile1 (writer ESRISHAPE_1)
    -> GeometryExtractor_15
StringConcatenator_17
    ATTRLIST = bestandsnaam
    ACTION = Overwrite Existing Attributes
    PARM_LINE = @Value(bestandsnaam)
    -> Shapefile100 (writer ESRISHAPE_1)
    -> GeometryExtractor_16
StringConcatenator_18
    ATTRLIST = bestandsnaam
    ACTION = Overwrite Existing Attributes
    PARM_LINE = @Value(bestandsnaam)
    -> Shapefile10000 (writer ESRISHAPE_1)
    -> GeometryExtractor_17

Bookmark: CSV maken
GeometryExtractor
    REMOVE_GEOMETRY = No
    ATTR = geometry
    OGC_WKT_PRECISION_DISPLAY = Shortened 64-bit
    KIND_LONG = OGC Well Known Text
    OGCVERSION = 1.1
    -> AttributeManager_37
AttributeManager_37
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
    -> imgeo_extractie.vw_imgeo_scheiding (writer CSV_1)
imgeo_extractie.vw_imgeo_scheiding (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-type char(200), plus-type char(200), geometry float
GeometryExtractor_2
    REMOVE_GEOMETRY = No
    ATTR = geometry
    OGC_WKT_PRECISION_DISPLAY = Shortened 64-bit
    KIND_LONG = OGC Well Known Text
    OGCVERSION = 1.1
    -> AttributeManager_38
AttributeManager_38
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
    -> imgeo_extractie.vw_imgeo_scheiding00 (writer CSV_1)
imgeo_extractie.vw_imgeo_scheiding00 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-type char(200), plus-type char(200), geometry float
GeometryExtractor_3
    REMOVE_GEOMETRY = No
    ATTR = geometry
    OGC_WKT_PRECISION_DISPLAY = Shortened 64-bit
    KIND_LONG = OGC Well Known Text
    OGCVERSION = 1.1
    -> AttributeManager_39
AttributeManager_39
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
    -> imgeo_extractie.vw_imgeo_scheiding0001 (writer CSV_1)
imgeo_extractie.vw_imgeo_scheiding0001 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-type char(200), plus-type char(200), geometry float
AttributeManager_40
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
    -> imgeo_extractie.vw_imgeo_scheiding000100 (writer CSV_1)
imgeo_extractie.vw_imgeo_scheiding000100 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-type char(200), plus-type char(200), geometry float
AttributeManager_41
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
    -> imgeo_extractie.vw_imgeo_scheiding000101 (writer CSV_1)
imgeo_extractie.vw_imgeo_scheiding000101 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-type char(200), plus-type char(200), geometry float
GeometryExtractor_6
    REMOVE_GEOMETRY = No
    ATTR = geometry
    OGC_WKT_PRECISION_DISPLAY = Shortened 64-bit
    KIND_LONG = OGC Well Known Text
    OGCVERSION = 1.1
    -> AttributeManager_42
AttributeManager_42
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
    -> imgeo_extractie.vw_imgeo_scheiding000102 (writer CSV_1)
imgeo_extractie.vw_imgeo_scheiding000102 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), geometry float
GeometryExtractor_7
    REMOVE_GEOMETRY = No
    ATTR = geometry
    OGC_WKT_PRECISION_DISPLAY = Shortened 64-bit
    KIND_LONG = OGC Well Known Text
    OGCVERSION = 1.1
    -> AttributeManager_43
AttributeManager_43
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfunctie > bgt-functie
      RENAME_SET_VALUE plusfunct > plus-functie
    -> imgeo_extractie.vw_imgeo_scheiding00010200 (writer CSV_1)
imgeo_extractie.vw_imgeo_scheiding00010200 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-functie char(200), plus-functie char(200), geometry float
GeometryExtractor_8
    REMOVE_GEOMETRY = No
    ATTR = geometry
    OGC_WKT_PRECISION_DISPLAY = Shortened 64-bit
    KIND_LONG = OGC Well Known Text
    OGCVERSION = 1.1
    -> AttributeManager_44
AttributeManager_44
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE plustype > plus-type
      RENAME_SET_VALUE hoortbij > hoortbijtypeoverbrugging
      RENAME_SET_VALUE isbeweegb > overbruggingisbeweegbaar
    -> imgeo_extractie.vw_imgeo_scheiding00010201 (writer CSV_1)
imgeo_extractie.vw_imgeo_scheiding00010201 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), plus-type char(200), hoortbijtypeoverbrugging char(200), overbruggingisbeweegbaar char(1), geometry float
GeometryExtractor_9
    REMOVE_GEOMETRY = No
    ATTR = geometry
    OGC_WKT_PRECISION_DISPLAY = Shortened 64-bit
    KIND_LONG = OGC Well Known Text
    OGCVERSION = 1.1
    -> AttributeManager_45
AttributeManager_45
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
    -> imgeo_extractie.vw_imgeo_scheiding00010202 (writer CSV_1)
imgeo_extractie.vw_imgeo_scheiding00010202 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), geometry float
GeometryExtractor_10
    REMOVE_GEOMETRY = No
    ATTR = geometry
    OGC_WKT_PRECISION_DISPLAY = Shortened 64-bit
    KIND_LONG = OGC Well Known Text
    OGCVERSION = 1.1
    -> AttributeManager_46
AttributeManager_46
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bagpndid > identificatiebagpnd
    -> imgeo_extractie.vw_imgeo_scheiding00010203 (writer CSV_1)
imgeo_extractie.vw_imgeo_scheiding00010203 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), identificatiebagpnd char(20), geometry float
GeometryExtractor_11
    REMOVE_GEOMETRY = No
    ATTR = geometry
    OGC_WKT_PRECISION_DISPLAY = Shortened 64-bit
    KIND_LONG = OGC Well Known Text
    OGCVERSION = 1.1
    -> AttributeManager_47
AttributeManager_47
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
    -> imgeo_extractie.vw_imgeo_scheiding00010204 (writer CSV_1)
imgeo_extractie.vw_imgeo_scheiding00010204 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), optalud char(1), hoortbijtypeoverbrugging char(200), geometry float
GeometryExtractor_12
    REMOVE_GEOMETRY = No
    ATTR = geometry
    OGC_WKT_PRECISION_DISPLAY = Shortened 64-bit
    KIND_LONG = OGC Well Known Text
    OGCVERSION = 1.1
    -> AttributeManager_48
AttributeManager_48
    ATTR_TABLE:
      RENAME_SET_VALUE namespace > identificatie_namespace
      RENAME_SET_VALUE lokaalid > identificatie_lokaalid
    -> imgeo_extractie.vw_imgeo_scheiding0000010500 (writer CSV_1)
imgeo_extractie.vw_imgeo_scheiding0000010500 (writer CSV_1) [off]
    attributes: identificatie_namespace char(8), identificatie_lokaalid char(38), nauwkeurig int, dat_inwinn auto, inw_instan char(40), inw_methid char(40), geometry float
GeometryExtractor_13
    REMOVE_GEOMETRY = No
    ATTR = geometry
    OGC_WKT_PRECISION_DISPLAY = Shortened 64-bit
    KIND_LONG = OGC Well Known Text
    OGCVERSION = 1.1
    -> AttributeManager_49
AttributeManager_49
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bagoprid > identificatieBAGOPR
      RENAME_SET_VALUE oprtype > openbareruimtetype
      RENAME_SET_VALUE labeltekst > label_tekst
    -> imgeo_extractie.vw_imgeo_scheiding0001020400 (writer CSV_1)
imgeo_extractie.vw_imgeo_scheiding0001020400 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), identificatieBAGOPR float, openbareruimtetype char(200), label_tekst char(200), hoek float, geometry float
GeometryExtractor_14
    REMOVE_GEOMETRY = No
    ATTR = geometry
    OGC_WKT_PRECISION_DISPLAY = Shortened 64-bit
    KIND_LONG = OGC Well Known Text
    OGCVERSION = 1.1
    -> AttributeManager_50
AttributeManager_50
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bagpndid > identificatiebagpnd
      RENAME_SET_VALUE bagvbolgst > id_bagvbolaagste_huisnummer
      RENAME_SET_VALUE bagvbohgst > id_bagvbohoogste_huisnummer
      RENAME_SET_VALUE labeltekst > label_tekst
    -> imgeo_extractie.vw_imgeo_scheiding0001020401 (writer CSV_1)
imgeo_extractie.vw_imgeo_scheiding0001020401 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), identificatiebagpnd char(20), id_bagvbolaagste_huisnummer char(20), id_bagvbohoogste_huisnummer char(20), label_tekst char(200), hoek float, geometry float
GeometryExtractor_15
    REMOVE_GEOMETRY = No
    ATTR = geometry
    OGC_WKT_PRECISION_DISPLAY = Shortened 64-bit
    KIND_LONG = OGC Well Known Text
    OGCVERSION = 1.1
    -> AttributeManager_51
AttributeManager_51
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfunctie > bgt-functie
      RENAME_SET_VALUE bgtfysvkn > bgt-fysiekvoorkomen
      RENAME_SET_VALUE plusfunct > plus-functie
      RENAME_SET_VALUE plusfysvkn > plus-fysiekvoorkomen
    -> imgeo_extractie.vw_imgeo_scheiding0001020402 (writer CSV_1)
imgeo_extractie.vw_imgeo_scheiding0001020402 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-functie char(200), bgt-fysiekvoorkomen char(200), optalud char(1), plus-functie char(200), plus-fysiekvoorkomen char(200), geometry float
GeometryExtractor_16
    REMOVE_GEOMETRY = No
    ATTR = geometry
    OGC_WKT_PRECISION_DISPLAY = Shortened 64-bit
    KIND_LONG = OGC Well Known Text
    OGCVERSION = 1.1
    -> AttributeManager_52
AttributeManager_52
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfysvkn > bgt-fysiekvoorkomen
      RENAME_SET_VALUE plusfysvkn > plus-fysiekvoorkomen
    -> imgeo_extractie.vw_imgeo_scheiding0001020403 (writer CSV_1)
imgeo_extractie.vw_imgeo_scheiding0001020403 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), plus-status char(8), bgt-fysiekvoorkomen char(200), optalud char(1), plus-fysiekvoorkomen char(200), geometry float
GeometryExtractor_17
    REMOVE_GEOMETRY = No
    ATTR = geometry
    OGC_WKT_PRECISION_DISPLAY = Shortened 64-bit
    KIND_LONG = OGC Well Known Text
    OGCVERSION = 1.1
    -> AttributeManager_53
AttributeManager_53
    ATTR_TABLE:
      RENAME_SET_VALUE namespace > identificatie_namespace
      RENAME_SET_VALUE lokaalid > identificatie_lokaalid
      RENAME_SET_VALUE begintijd > objectbegintijd
      RENAME_SET_VALUE einddtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
    -> imgeo_extractie.vw_imgeo_scheiding0001020404 (writer CSV_1)
imgeo_extractie.vw_imgeo_scheiding0001020404 (writer CSV_1)
    attributes: identificatie_namespace char(8), identificatie_lokaalid char(38), objectbegintijd char(8), objecteindtijd char(8), tijdstipregistratie char(20), eindregistratie char(20), lv-publicatiedatum char(20), bronhouder char(40), inonderzoek char(1), relatievehoogteligging int, bgt-status char(8), bgt-type char(8), plus-status char(8), plus-type char(200), geometry float

Bookmark: Totaalgebied shapefiles
Note: lijnen
Note: punten
Note: vlakken
