FME workspace aanmaak_esrishape_uit_DB_BGT.fmw
Title: BGT producten
Description: Frietsnijder shapefiles

Parameters:
- SourceDataset_POSTGIS = bgt_dev_local   # Connection
- DestDataset_ESRISHAPE2 = $(FME_MF_DIR)esri_shape   # Destination Esri Shapefolder
- DestDataset_ESRISHAPE3 = $(FME_MF_DIR)esri_shape\Totaalgebied   # Destination Esri Shapefolder
- SourceDataset_POSTGIS_3 = bgt_dev_local   # Connection

Readers:
- POSTGIS_1: POSTGIS from $(SourceDataset_POSTGIS) in EPSG:28992
- POSTGIS_2: POSTGIS from $(SourceDataset_POSTGIS_3) in EPSG:28992

Writers:
- ESRISHAPE_1: ESRISHAPE to $(DestDataset_ESRISHAPE2) in EPSG:28992
- ESRISHAPE_2: ESRISHAPE to $(DestDataset_ESRISHAPE2)
- ESRISHAPE_3: ESRISHAPE to $(DestDataset_ESRISHAPE3)

imgeo_extractie.vw_imgeo_straatmeubilair (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_14
Note: Data Flow
AttributeManager_14
    ATTR_TABLE = SET_TO bestandsnaam = FME_CONDITIONAL:DEFAULT_VALUE'_FME_NO_OP_'BOOL_OP;AND;COMPOSITE_TEST;<Unused>;TEST bestandsnaam ATTRIBUTE_VALUE_NULL _FME_BLANK_STRING_'@Value(bestandsnaam_plus)'FME_NUM_CONDITIONS2___
    -> verzamelaar
imgeo_extractie.vw_imgeo_put (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_12
AttributeManager_12
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar
imgeo_extractie.vw_imgeo_mast (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_9
AttributeManager_9
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar
imgeo_extractie.vw_imgeo_kast (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager
AttributeManager
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar
imgeo_extractie.vw_imgeo_installatie (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_8
AttributeManager_8
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar
imgeo_extractie.vw_imgeo_bord (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_5
AttributeManager_5
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar
imgeo_extractie.vw_imgeo_bak (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_4
AttributeManager_4
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar
imgeo_extractie.vw_imgeo_weginrichtingselement (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_20
AttributeManager_20
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_8
GeometryFilter_8
    BREAK_AGG = Yes
    INSTANTIATE = Yes
    GEOM_PORT_NAMES = Point Line Area Surface
    POINT -> AttributeManager_34
    LINE -> AttributeManager_35
    AREA -> AttributeManager_36
    SURFACE -> AttributeManager_36
AttributeManager_34
    ATTR_TABLE = SET_TO bestandsnaam = FME_CONDITIONAL:DEFAULT_VALUE'_FME_NO_OP_'BOOL_OP;OR;COMPOSITE_TEST;<Unused>;TEST @Value(bestandsnaam) IN BGTPLUS_WGI_wegmarkering,BGTPLUS_WGI_wildrooster,BGTPLUS_WGI_rooster,BGTPLUS_WGI_geleideconstructie,BGTPLUS_WGI_boomspiegel,BGTPLUS_WGI_onbekend'@Value(bestandsnaam)_P'FME_NUM_CONDITIONS2___
    -> verzamelaar
AttributeManager_35
    ATTR_TABLE = SET_TO bestandsnaam = FME_CONDITIONAL:DEFAULT_VALUE'_FME_NO_OP_'BOOL_OP;OR;COMPOSITE_TEST;<Unused>;TEST @Value(bestandsnaam) IN BGTPLUS_WGI_wegmarkering,BGTPLUS_WGI_wildrooster,BGTPLUS_WGI_rooster,BGTPLUS_WGI_geleideconstructie,BGTPLUS_WGI_boomspiegel,BGTPLUS_WGI_onbekend'@Value(bestandsnaam)_L'FME_NUM_CONDITIONS2___
    -> verzamelaar_2
AttributeManager_36
    ATTR_TABLE = SET_TO bestandsnaam = FME_CONDITIONAL:DEFAULT_VALUE'_FME_NO_OP_'BOOL_OP;OR;COMPOSITE_TEST;<Unused>;TEST @Value(bestandsnaam) IN BGTPLUS_WGI_wegmarkering,BGTPLUS_WGI_wildrooster,BGTPLUS_WGI_rooster,BGTPLUS_WGI_geleideconstructie,BGTPLUS_WGI_boomspiegel,BGTPLUS_WGI_onbekend'@Value(bestandsnaam)_V'FME_NUM_CONDITIONS2___
    -> verzamelaar_3
imgeo_extractie.vw_imgeo_waterinrichtingselement (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_19
AttributeManager_19
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_3
GeometryFilter_3
    BREAK_AGG = Yes
    INSTANTIATE = Yes
    GEOM_PORT_NAMES = Point Line
    POINT -> AttributeManager_32
    LINE -> AttributeManager_33
AttributeManager_32
    ATTR_TABLE = SET_TO bestandsnaam = FME_CONDITIONAL:DEFAULT_VALUE'_FME_NO_OP_'BOOL_OP;OR;COMPOSITE_TEST;<Unused>;TEST @Value(bestandsnaam) = BGTPLUS_WDI_onbekend'@Value(bestandsnaam)_P'FME_NUM_CONDITIONS2___
    -> verzamelaar
AttributeManager_33
    ATTR_TABLE = SET_TO bestandsnaam = FME_CONDITIONAL:DEFAULT_VALUE'_FME_NO_OP_'BOOL_OP;OR;COMPOSITE_TEST;<Unused>;TEST @Value(bestandsnaam) = BGTPLUS_WDI_onbekend'@Value(bestandsnaam)_L'FME_NUM_CONDITIONS2___
    -> verzamelaar_2
imgeo_extractie.vw_imgeo_vegetatieobject (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_18
AttributeManager_18
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_7
GeometryFilter_7
    BREAK_AGG = Yes
    INSTANTIATE = Yes
    GEOM_PORT_NAMES = Point Line Area Surface
    POINT -> AttributeManager_29
    LINE -> AttributeManager_30
    AREA -> AttributeManager_31
    SURFACE -> AttributeManager_31
AttributeManager_29
    ATTR_TABLE = SET_TO bestandsnaam = FME_CONDITIONAL:DEFAULT_VALUE'_FME_NO_OP_'BOOL_OP;OR;COMPOSITE_TEST;<Unused>;TEST @Value(bestandsnaam) IN BGTPLUS_VGT_haag,BGTPLUS_VGT_onbekend'@Value(bestandsnaam)_P'FME_NUM_CONDITIONS2___
    -> verzamelaar
AttributeManager_30
    ATTR_TABLE = SET_TO bestandsnaam = FME_CONDITIONAL:DEFAULT_VALUE'_FME_NO_OP_'BOOL_OP;OR;COMPOSITE_TEST;<Unused>;TEST @Value(bestandsnaam) IN BGTPLUS_VGT_haag,BGTPLUS_VGT_onbekend'@Value(bestandsnaam)_L'FME_NUM_CONDITIONS2___
    -> verzamelaar_2
AttributeManager_31
    ATTR_TABLE = SET_TO bestandsnaam = FME_CONDITIONAL:DEFAULT_VALUE'_FME_NO_OP_'BOOL_OP;OR;COMPOSITE_TEST;<Unused>;TEST @Value(bestandsnaam) IN BGTPLUS_VGT_haag,BGTPLUS_VGT_onbekend'@Value(bestandsnaam)_V'FME_NUM_CONDITIONS2___
    -> verzamelaar_3
imgeo_extractie.vw_imgeo_sensor (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_17
AttributeManager_17
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_4
GeometryFilter_4
    BREAK_AGG = Yes
    INSTANTIATE = Yes
    GEOM_PORT_NAMES = Point Line
    POINT -> AttributeManager_27
    LINE -> AttributeManager_28
AttributeManager_27
    ATTR_TABLE = SET_TO bestandsnaam = FME_CONDITIONAL:DEFAULT_VALUE'_FME_NO_OP_'BOOL_OP;OR;COMPOSITE_TEST;<Unused>;TEST @Value(bestandsnaam) = BGTPLUS_SSR_onbekend'@Value(bestandsnaam)_P'FME_NUM_CONDITIONS2___
    -> verzamelaar
AttributeManager_28
    ATTR_TABLE = SET_TO bestandsnaam = FME_CONDITIONAL:DEFAULT_VALUE'_FME_NO_OP_'BOOL_OP;OR;COMPOSITE_TEST;<Unused>;TEST @Value(bestandsnaam) = BGTPLUS_SSR_onbekend'@Value(bestandsnaam)_L'FME_NUM_CONDITIONS2___
    -> verzamelaar_2
imgeo_extractie.vw_imgeo_scheiding (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_2
AttributeManager_2
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_5
GeometryFilter_5
    BREAK_AGG = Yes
    INSTANTIATE = Yes
    GEOM_PORT_NAMES = Line Area Surface
    LINE -> AttributeManager_3
    SURFACE -> AttributeManager_24
    AREA -> AttributeManager_24
AttributeManager_3
    ATTR_TABLE = SET_TO bestandsnaam = FME_CONDITIONAL:DEFAULT_VALUE'_FME_NO_OP_'BOOL_OP;OR;COMPOSITE_TEST;<Unused>;TEST @Value(bestandsnaam) IN BGT_SDG_muur,BGT_SDG_kademuur,BGT_SDG_transitie,BGTPLUS_SDG_onbekend'@Value(bestandsnaam)_L'FME_NUM_CONDITIONS2___
    -> verzamelaar_2
AttributeManager_24
    ATTR_TABLE = SET_TO bestandsnaam = FME_CONDITIONAL:DEFAULT_VALUE'_FME_NO_OP_'BOOL_OP;OR;COMPOSITE_TEST;<Unused>;TEST @Value(bestandsnaam) IN BGT_SDG_muur,BGT_SDG_kademuur,BGT_SDG_transitie,BGTPLUS_SDG_onbekend'@Value(bestandsnaam)_V'FME_NUM_CONDITIONS2___
    -> verzamelaar_3
imgeo_extractie.vw_imgeo_overigescheiding (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_16
AttributeManager_16
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_6
GeometryFilter_6
    BREAK_AGG = Yes
    INSTANTIATE = Yes
    GEOM_PORT_NAMES = Line Area Surface
    LINE -> AttributeManager_25
    AREA -> AttributeManager_26
    SURFACE -> AttributeManager_26
AttributeManager_25
    ATTR_TABLE = SET_TO bestandsnaam = FME_CONDITIONAL:DEFAULT_VALUE'_FME_NO_OP_'BOOL_OP;OR;COMPOSITE_TEST;<Unused>;TEST @Value(bestandsnaam) IN BGTPLUS_OSDG_muur,BGTPLUS_OSDG_kademuur,BGTPLUS_OSDG_onbekend'@Value(bestandsnaam)_L'FME_NUM_CONDITIONS2___
    -> verzamelaar_2
AttributeManager_26
    ATTR_TABLE = SET_TO bestandsnaam = FME_CONDITIONAL:DEFAULT_VALUE'_FME_NO_OP_'BOOL_OP;OR;COMPOSITE_TEST;<Unused>;TEST @Value(bestandsnaam) IN BGTPLUS_OSDG_muur,BGTPLUS_OSDG_kademuur,BGTPLUS_OSDG_onbekend'@Value(bestandsnaam)_V'FME_NUM_CONDITIONS2___
    -> verzamelaar_3
imgeo_extractie.vw_imgeo_kunstwerkdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_15
AttributeManager_15
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_9
GeometryFilter_9
    BREAK_AGG = Yes
    INSTANTIATE = Yes
    GEOM_PORT_NAMES = Point Line Area Surface
    LINE -> AttributeManager_21
    POINT -> AttributeManager_22
    AREA -> AttributeManager_23
    SURFACE -> AttributeManager_23
AttributeManager_22
    ATTR_TABLE = SET_TO bestandsnaam = FME_CONDITIONAL:DEFAULT_VALUE'_FME_NO_OP_'BOOL_OP;OR;COMPOSITE_TEST;<Unused>;TEST @Value(bestandsnaam) IN BGT_KDL_hoogspanningsmast,BGT_KDL_transitie, BGT_KDL_onbekend'@Value(bestandsnaam)_P'FME_NUM_CONDITIONS2___
    -> verzamelaar
Note: imgeo objecten: geometrietype punten
verzamelaar: Counter
    START = 0
    CNT_ATTR = _count
    DOMAIN = counter
    SCOPE = Global
    -> SpatialRelator_2 [input 1]
    -> StringConcatenator_19
Note: Shapefiles_totaalgebied
StringConcatenator_19
    ACTION = Overwrite Existing Attributes
    ATTRLIST = bestandsnaam
    PARM_LINE = @Value(bestandsnaam)
    -> Shapefile1 (writer ESRISHAPE_3)
Shapefile1 (writer ESRISHAPE_3)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
AttributeManager_21
    ATTR_TABLE = SET_TO bestandsnaam = FME_CONDITIONAL:DEFAULT_VALUE'_FME_NO_OP_'BOOL_OP;OR;COMPOSITE_TEST;<Unused>;TEST @Value(bestandsnaam) IN BGT_KDL_stuw,BGT_KDL_transitie,BGTPLUS_KDL_duiker,BGTPLUS_KDL_onbekend'@Value(bestandsnaam)_L'FME_NUM_CONDITIONS2___
    -> verzamelaar_2
Note: imgeo objecten: geometrietype lijnen
verzamelaar_2: Counter
    START = 0
    CNT_ATTR = _count
    DOMAIN = counter
    SCOPE = Global
    -> SpatialRelator_4 [input 1]
    -> StringConcatenator_20
StringConcatenator_20
    ACTION = Overwrite Existing Attributes
    ATTRLIST = bestandsnaam
    PARM_LINE = @Value(bestandsnaam)
    -> Shapefile100 (writer ESRISHAPE_3)
Shapefile100 (writer ESRISHAPE_3)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
AttributeManager_23
    ATTR_TABLE = SET_TO bestandsnaam = FME_CONDITIONAL:DEFAULT_VALUE'_FME_NO_OP_'BOOL_OP;OR;COMPOSITE_TEST;<Unused>;TEST @Value(bestandsnaam) IN BGT_KDL_hoogspanningsmast,BGT_KDL_transitie,BGT_KDL_stuw,BGTPLUS_KDL_duiker,BGTPLUS_KDL_onbekend'@Value(bestandsnaam)_V'FME_NUM_CONDITIONS2___
    -> verzamelaar_3
imgeo_extractie.vw_imgeo_overigbouwwerk (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_10
AttributeManager_10
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar_3
imgeo_extractie.vw_imgeo_gebouwinstallatie (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_7
AttributeManager_7
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar_3
Note: imgeo objecten: geometrietype vlakken
verzamelaar_3: Counter
    START = 0
    CNT_ATTR = _count
    DOMAIN = counter
    SCOPE = Global
    -> SpatialRelator_5 [input 1]
    -> StringConcatenator_21
Note: GebiedenRelatieBGTObjecten
StringConcatenator_21
    ACTION = Overwrite Existing Attributes
    ATTRLIST = bestandsnaam
    PARM_LINE = @Value(bestandsnaam)
    -> Shapefile10000 (writer ESRISHAPE_3)
Shapefile10000 (writer ESRISHAPE_3)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
imgeo_extractie.vw_imgeo_paal (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_11
AttributeManager_11
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> SpatialRelator_6 [input 1]
    -> StringConcatenator_22
StringConcatenator_22
    ACTION = Overwrite Existing Attributes
    ATTRLIST = bestandsnaam
    PARM_LINE = @Value(bestandsnaam)
    -> Shapefile1000000 (writer ESRISHAPE_3)
Shapefile1000000 (writer ESRISHAPE_3)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
imgeo_extractie.vw_imgeo_functioneelgebied (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text, naam varchar(200)
    -> AttributeManager_6
AttributeManager_6
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> SpatialRelator_7 [input 1]
    -> StringConcatenator_23
StringConcatenator_23
    ACTION = Overwrite Existing Attributes
    ATTRLIST = bestandsnaam
    PARM_LINE = @Value(bestandsnaam)
    -> Shapefile100000000 (writer ESRISHAPE_3)
Shapefile100000000 (writer ESRISHAPE_3)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
imgeo_extractie.vw_bgt_tunneldeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bestandsnaam text
    -> StringConcatenator_24
    -> SpatialRelator_8 [input 1]
StringConcatenator_24
    ACTION = Overwrite Existing Attributes
    ATTRLIST = bestandsnaam
    PARM_LINE = @Value(bestandsnaam)
    -> Shapefile100000001 (writer ESRISHAPE_3)
Shapefile100000001 (writer ESRISHAPE_3)
    attributes: namespace char(8), lokaalid char(38), begintijd date, einddtijd date, tijdreg char(20), eindreg char(20), lv_pubdat char(20), bronhoud char(40), inonderzk char(1), hoogtelig short, bgtstatus char(8), plusstatus char(8)
imgeo_extractie.vw_imgeo_spoor (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfunctie varchar(200), bestandsnaam text, plusfunct varchar(200), bestandsnaam_plus text
    -> AttributeManager_13
AttributeManager_13
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> SpatialRelator_3 [input 1]
    -> StringConcatenator_25
StringConcatenator_25
    ACTION = Overwrite Existing Attributes
    ATTRLIST = bestandsnaam
    PARM_LINE = @Value(bestandsnaam)
    -> Shapefile10000000100 (writer ESRISHAPE_3)
Shapefile10000000100 (writer ESRISHAPE_3)
    attributes: namespace char(8), lokaalid char(38), begintijd date, einddtijd date, tijdreg char(20), eindreg char(20), lv_pubdat char(20), bronhoud char(40), inonderzk char(1), hoogtelig short, bgtstatus char(8), plusstatus char(8), bgtfunctie char(200), plusfunct char(200)
imgeo_extractie.vw_bgt_overbruggingsdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), plustype varchar(200), bestandsnaam text, hoortbij varchar(200), isbeweegb varchar(1)
    -> StringConcatenator_26
    -> SpatialRelator_10 [input 1]
StringConcatenator_26
    ACTION = Overwrite Existing Attributes
    ATTRLIST = bestandsnaam
    PARM_LINE = @Value(bestandsnaam)
    -> Shapefile1000000010000 (writer ESRISHAPE_3)
Shapefile1000000010000 (writer ESRISHAPE_3)
    attributes: namespace char(8), lokaalid char(38), begintijd date, einddtijd date, tijdreg char(20), eindreg char(20), lv_pubdat char(20), bronhoud char(40), inonderzk char(1), hoogtelig short, bgtstatus char(8), plusstatus char(8), plustype char(200), hoortbij char(200), isbeweegb char(1)
imgeo_extractie.vw_bgt_ongeclassificeerdobject (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bestandsnaam text
    -> StringConcatenator_27
    -> SpatialRelator_11 [input 1]
StringConcatenator_27
    ACTION = Overwrite Existing Attributes
    ATTRLIST = bestandsnaam
    PARM_LINE = @Value(bestandsnaam)
    -> Shapefile100000001000000 (writer ESRISHAPE_3)
Shapefile100000001000000 (writer ESRISHAPE_3)
    attributes: namespace char(8), lokaalid char(38), begintijd date, einddtijd date, tijdreg char(20), eindreg char(20), lv_pubdat char(20), bronhoud char(40), inonderzk char(1), hoogtelig short, bgtstatus char(8), plusstatus char(8)
imgeo_extractie.vw_bgt_pand (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bestandsnaam text, bagpndid varchar(20)
    -> StringConcatenator_28
    -> SpatialRelator_12 [input 1]
StringConcatenator_28
    ACTION = Overwrite Existing Attributes
    ATTRLIST = bestandsnaam
    PARM_LINE = @Value(bestandsnaam)
    -> Shapefile10000000100000000 (writer ESRISHAPE_3)
Shapefile10000000100000000 (writer ESRISHAPE_3)
    attributes: namespace char(8), lokaalid char(38), begintijd date, einddtijd date, tijdreg char(20), eindreg char(20), lv_pubdat char(20), bronhoud char(40), inonderzk char(1), hoogtelig short, bgtstatus char(8), plusstatus char(8), bagpndid char(20)
imgeo_extractie.vw_bgt_kruinlijn (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), optalud varchar(1), bestandsnaam text, hoortbij varchar(200)
    -> StringConcatenator_29
    -> SpatialRelator_13 [input 1]
StringConcatenator_29
    ACTION = Overwrite Existing Attributes
    ATTRLIST = bestandsnaam
    PARM_LINE = @Value(bestandsnaam)
    -> Shapefile1000000010000000000 (writer ESRISHAPE_3)
Shapefile1000000010000000000 (writer ESRISHAPE_3)
    attributes: namespace char(8), lokaalid char(38), begintijd date, einddtijd date, tijdreg char(20), eindreg char(20), lv_pubdat char(20), bronhoud char(40), inonderzk char(1), hoogtelig short, bgtstatus char(8), plusstatus char(8), optalud char(1), hoortbij char(200)
imgeo_extractie.vw_bgt_plaatsbepalingspunt (reader POSTGIS_2)
    attributes: namespace varchar(8), lokaalid varchar(38), nauwkeurig int4, dat_inwinn date, inw_instan varchar(40), inw_methid varchar(40), bestandsnaam text
    -> StringConcatenator_30 [off]
    -> SpatialRelator_9 [input 1] [off]
StringConcatenator_30 [off]
    ACTION = Overwrite Existing Attributes
    ATTRLIST = bestandnaam
    PARM_LINE = @Value(bestandnaam)
    -> Shapefile100000001000000000000 (writer ESRISHAPE_3) [off]
Shapefile100000001000000000000 (writer ESRISHAPE_3) [off]
    attributes: namespace char(8), lokaalid char(38), nauwkeurig long, dat_inwinn date, inw_instan char(40), inw_methid char(40)
imgeo_extractie.vw_bgt_openbareruimtelabel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bagoprid varchar(20), oprtype varchar(200), bestandsnaam text, labeltekst varchar(200), hoek float4
    -> StringConcatenator_31
    -> SpatialRelator_14 [input 1]
StringConcatenator_31
    ACTION = Overwrite Existing Attributes
    ATTRLIST = bestandsnaam
    PARM_LINE = @Value(bestandsnaam)
    -> Shapefile10000000100000000000000 (writer ESRISHAPE_3)
Shapefile10000000100000000000000 (writer ESRISHAPE_3)
    attributes: namespace char(8), lokaalid char(38), begintijd date, einddtijd date, tijdreg char(20), eindreg char(20), lv_pubdat char(20), bronhoud char(40), inonderzk char(1), hoogtelig short, bgtstatus char(8), plusstatus char(8), bagoprid char(20), oprtype char(200), labeltekst char(200), hoek float
imgeo_extractie.vw_bgt_nummeraanduidingreeks (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bestandsnaam text, bagpndid varchar(20), bagvbolgst varchar(20), bagvbohgst varchar(20), labeltekst varchar(200), hoek float4
    -> StringConcatenator_32
    -> SpatialRelator_15 [input 1]
StringConcatenator_32
    ACTION = Overwrite Existing Attributes
    ATTRLIST = bestandsnaam
    PARM_LINE = @Value(bestandsnaam)
    -> Shapefile1000000010000000000000000 (writer ESRISHAPE_3)
Shapefile1000000010000000000000000 (writer ESRISHAPE_3)
    attributes: namespace char(8), lokaalid char(38), begintijd date, einddtijd date, tijdreg char(20), eindreg char(20), lv_pubdat char(20), bronhoud char(40), inonderzk char(1), hoogtelig short, bgtstatus char(8), plusstatus char(8), bagpndid char(20), bagvbolgst char(20), bagvbohgst char(20), labeltekst char(200), hoek float
imgeo_extractie.vw_bgt_ondersteunendwegdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfunctie varchar(200), bestandsnaam text, bgtfysvkn varchar(200), optalud varchar(1), plusfunct varchar(200), plusfysvkn varchar(200)
    -> StringConcatenator_33
    -> SpatialRelator [input 1]
StringConcatenator_33
    ACTION = Overwrite Existing Attributes
    ATTRLIST = bestandsnaam
    PARM_LINE = @Value(bestandsnaam)
    -> Shapefile100000001000000000000000000 (writer ESRISHAPE_3)
Shapefile100000001000000000000000000 (writer ESRISHAPE_3)
    attributes: namespace char(8), lokaalid char(38), begintijd date, einddtijd date, tijdreg char(20), eindreg char(20), lv_pubdat char(20), bronhoud char(40), inonderzk char(1), hoogtelig short, bgtstatus char(8), plusstatus char(8), bgtfunctie char(200), bgtfysvkn char(200), optalud char(1), plusfunct char(200), plusfysvkn char(200)
imgeo_extractie.vw_bgt_wegdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfunctie varchar(200), bestandsnaam text, bgtfysvkn varchar(200), optalud varchar(1), plusfunct varchar(200), plusfysvkn varchar(200)
    -> StringConcatenator_34
    -> SpatialRelator [input 1]
StringConcatenator_34
    ACTION = Overwrite Existing Attributes
    ATTRLIST = bestandsnaam
    PARM_LINE = @Value(bestandsnaam)
    -> Shapefile10000000100000000000000000000 (writer ESRISHAPE_3)
Shapefile10000000100000000000000000000 (writer ESRISHAPE_3)
    attributes: namespace char(8), lokaalid char(38), begintijd date, einddtijd date, tijdreg char(20), eindreg char(20), lv_pubdat char(20), bronhoud char(40), inonderzk char(1), hoogtelig short, bgtstatus char(8), plusstatus char(8), bgtfunctie char(200), bgtfysvkn char(200), optalud char(1), plusfunct char(200), plusfysvkn char(200)
imgeo_extractie.vw_bgt_begroeidterreindeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfysvkn varchar(200), bestandsnaam text, optalud varchar(1), plusfysvkn varchar(200)
    -> StringConcatenator_35
    -> SpatialRelator_16 [input 1]
StringConcatenator_35
    ACTION = Overwrite Existing Attributes
    ATTRLIST = bestandsnaam
    PARM_LINE = @Value(bestandsnaam)
    -> Shapefile1000000010000000000000000000000 (writer ESRISHAPE_3)
Shapefile1000000010000000000000000000000 (writer ESRISHAPE_3)
    attributes: namespace char(8), lokaalid char(38), begintijd date, einddtijd date, tijdreg char(20), eindreg char(20), lv_pubdat char(20), bronhoud char(40), inonderzk char(1), hoogtelig short, bgtstatus char(8), plusstatus char(8), bgtfysvkn char(200), optalud char(1), plusfysvkn char(200)
imgeo_extractie.vw_bgt_onbegroeidterreindeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfysvkn varchar(200), bestandsnaam text, optalud varchar(1), plusfysvkn varchar(200)
    -> StringConcatenator_36
    -> SpatialRelator_16 [input 1]
StringConcatenator_36
    ACTION = Overwrite Existing Attributes
    ATTRLIST = bestandsnaam
    PARM_LINE = @Value(bestandsnaam)
    -> Shapefile1000000010000000000000000000001 (writer ESRISHAPE_3)
Shapefile1000000010000000000000000000001 (writer ESRISHAPE_3)
    attributes: namespace char(8), lokaalid char(38), begintijd date, einddtijd date, tijdreg char(20), eindreg char(20), lv_pubdat char(20), bronhoud char(40), inonderzk char(1), hoogtelig short, bgtstatus char(8), plusstatus char(8), bgtfysvkn char(200), optalud char(1), plusfysvkn char(200)
imgeo_extractie.vw_bgt_ondersteunendwaterdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200)
    -> StringConcatenator_37
    -> SpatialRelator_17 [input 1]
StringConcatenator_37
    ACTION = Overwrite Existing Attributes
    ATTRLIST = bestandsnaam
    PARM_LINE = @Value(bestandsnaam)
    -> Shapefile100000001000000000000000000000100 (writer ESRISHAPE_3)
Shapefile100000001000000000000000000000100 (writer ESRISHAPE_3)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
imgeo_extractie.vw_bgt_waterdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), bgttype varchar(200), bestandsnaam text, plusstatus varchar(8)
    -> StringConcatenator_38
    -> SpatialRelator_17 [input 1]
StringConcatenator_38
    ACTION = Overwrite Existing Attributes
    ATTRLIST = bestandsnaam
    PARM_LINE = @Value(bestandsnaam)
    -> Shapefile10000000100000000000000000000010000 (writer ESRISHAPE_3)
Shapefile10000000100000000000000000000010000 (writer ESRISHAPE_3)
    attributes: namespace char(8), lokaalid char(38), begintijd date, einddtijd date, tijdreg char(20), eindreg char(20), lv_pubdat char(20), bronhoud char(40), inonderzk char(1), hoogtelig short, bgtstatus char(8), bgttype char(200), plusstatus char(8)
imgeo.pdt_kaartblad (reader POSTGIS_1)
    attributes: id serial,PRIKEY, naam varchar(200), big_id int4
    -> AttributeFilter
Note: kaartbladen
AttributeFilter
    ATTR_VALUES = <EMPTY>,<MISSING>,<NULL>,<UNFILTERED>,2
    ATTR_NAME = big_id
    2 -> SpikeRemover_2
SpikeRemover_2
    SPIKEANGLE = 0.0001
    UNCHANGED -> SliverRemover_3
    CHANGED -> SliverRemover_3
SliverRemover_3
    REPAIR_METHOD = Longest Boundary
    REPAIRED -> SpatialRelator_2 [input 2]
    REPAIRED -> SpatialRelator_4 [input 2]
    REPAIRED -> SpatialRelator_5 [input 2]
    REPAIRED -> SpatialRelator_3 [input 2]
    REPAIRED -> SpatialRelator_6 [input 2]
    REPAIRED -> SpatialRelator_7 [input 2]
    REPAIRED -> SpatialRelator_8 [input 2]
    REPAIRED -> SpatialRelator_9 [input 2]
    REPAIRED -> SpatialRelator_10 [input 2]
    REPAIRED -> SpatialRelator_11 [input 2]
    REPAIRED -> SpatialRelator_12 [input 2]
    REPAIRED -> SpatialRelator_13 [input 2]
    REPAIRED -> SpatialRelator_14 [input 2]
    REPAIRED -> SpatialRelator_15 [input 2]
    REPAIRED -> SpatialRelator_16 [input 2]
    REPAIRED -> SpatialRelator_17 [input 2]
    REPAIRED -> SpatialRelator [input 2]
Note: shapesbestandsnaam
Note: Shapefilrs per gebied
Note: Punten
imgeo_extractie.vw_imgeo_kunstwerkdeel_point (writer ESRISHAPE_1)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
Note: Lijnen
imgeo_extractie.vw_imgeo_kunstwerkdeel_line (writer ESRISHAPE_1)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
Note: Vlakken
imgeo_extractie.vw_imgeo_kunstwerkdeel_polygon (writer ESRISHAPE_1)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
imgeo_extractie.vw_imgeo_spoor00 (writer ESRISHAPE_1)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
imgeo_extractie.vw_imgeo_spoor0000 (writer ESRISHAPE_1)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
Shapefile1010000 (writer ESRISHAPE_2)
    attributes: namespace char(8), lokaalid char(38), begintijd date, einddtijd date, tijdreg char(20), eindreg char(20), lv_pubdat char(20), bronhoud char(40), inonderzk char(1), hoogtelig short, bgtstatus char(8), plusstatus char(8)
Shapefile101000000 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgtfunctie char(200), plusfunct char(200)
Shapefile1010001 (writer ESRISHAPE_2)
    attributes: namespace char(8), lokaalid char(38), begintijd date, einddtijd date, tijdreg char(20), eindreg char(20), lv_pubdat char(20), bronhoud char(40), inonderzk char(1), hoogtelig short, bgtstatus char(8), plusstatus char(8), plustype char(200), hoortbij char(200), isbeweegb char(1)
Shapefile1010002 (writer ESRISHAPE_2)
    attributes: namespace char(8), lokaalid char(38), begintijd date, einddtijd date, tijdreg char(20), eindreg char(20), lv_pubdat char(20), bronhoud char(40), inonderzk char(1), hoogtelig short, bgtstatus char(8), plusstatus char(8)
Shapefile1010003 (writer ESRISHAPE_2)
    attributes: namespace char(8), lokaalid char(38), begintijd date, einddtijd date, tijdreg char(20), eindreg char(20), lv_pubdat char(20), bronhoud char(40), inonderzk char(1), hoogtelig short, bgtstatus char(8), plusstatus char(8), bagpndid char(20)
Shapefile101000300 (writer ESRISHAPE_2)
    attributes: namespace char(8), lokaalid char(38), begintijd date, einddtijd date, tijdreg char(20), eindreg char(20), lv_pubdat char(20), bronhoud char(40), inonderzk char(1), hoogtelig short, bgtstatus char(8), plusstatus char(8), optalud char(1), hoortbij char(200)
imgeo_extractie.vw_imgeo_spoor00000000 (writer ESRISHAPE_1) [off]
    attributes: namespace char(8), lokaalid char(38), nauwkeurig long, dat_inwinn date, inw_instan char(40), inw_methid char(40)
Shapefile10100 (writer ESRISHAPE_2)
    attributes: namespace char(8), lokaalid char(38), begintijd date, einddtijd date, tijdreg char(20), eindreg char(20), lv_pubdat char(20), bronhoud char(40), inonderzk char(1), hoogtelig short, bgtstatus char(8), plusstatus char(8), bagoprid char(20), oprtype char(200), labeltekst char(200), hoek float
Shapefile101 (writer ESRISHAPE_2)
    attributes: namespace char(8), lokaalid char(38), begintijd date, einddtijd date, tijdreg char(20), eindreg char(20), lv_pubdat char(20), bronhoud char(40), inonderzk char(1), hoogtelig short, bgtstatus char(8), plusstatus char(8), bagpndid char(20), bagvbolgst char(20), bagvbohgst char(20), labeltekst char(200), hoek float
Shapefile1 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgtfunctie char(200), bgtfysvkn char(200), optalud char(1), plusfunct char(200), plusfysvkn char(200)
Shapefile100 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgtfysvkn char(200), optalud char(1), plusfysvkn char(200)
Shapefile10000 (writer ESRISHAPE_2)
    attributes: namespace char(8), lokaalid char(38), begintijd date, einddtijd date, tijdreg char(20), eindreg char(20), lv_pubdat char(20), bronhoud char(40), inonderzk char(1), hoogtelig short, bgtstatus char(8), bgttype char(200), plusstatus char(8), plustype char(200)

Bookmark: GebiedenRelatieBGT_Objecten
SpatialRelator_2
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_2
ListExploder_2
    INDEX_ATTR = _element_index
    ATTR_CONFLICT_RES = Use Incoming List
    ATTR_ACCUM_MODE = Merge Incoming List
    LIST_ATTR = _relationships{}
    ELEMENTS -> StringConcatenator_2
SpatialRelator_4
    CURVE_BOUNDARY_RULE_PARAM = Default Rule
    CALC_CARD = No
    LIST_NAME = _relationships
    SUCCESS_ATTR = _related_candidates
    AGGREGATE_HANDLING = Yes
    PREDICATES = INTERSECTS CONTAINS
    -> ListExploder_4
ListExploder_4
    INDEX_ATTR = _element_index
    ATTR_CONFLICT_RES = Use Incoming List
    ATTR_ACCUM_MODE = Merge Incoming List
    LIST_ATTR = _relationships{}
    ELEMENTS -> StringConcatenator_5
SpatialRelator_5
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_5
ListExploder_5
    INDEX_ATTR = _element_index
    ATTR_CONFLICT_RES = Use Incoming List
    ATTR_ACCUM_MODE = Merge Incoming List
    LIST_ATTR = _relationships{}
    ELEMENTS -> StringConcatenator_6
SpatialRelator_6
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_6
ListExploder_6
    INDEX_ATTR = _element_index
    ATTR_CONFLICT_RES = Use Incoming List
    ATTR_ACCUM_MODE = Merge Incoming List
    LIST_ATTR = _relationships{}
    ELEMENTS -> StringConcatenator_7
SpatialRelator_7
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_7
ListExploder_7
    INDEX_ATTR = _element_index
    ATTR_CONFLICT_RES = Use Incoming List
    ATTR_ACCUM_MODE = Merge Incoming List
    LIST_ATTR = _relationships{}
    ELEMENTS -> StringConcatenator_8
SpatialRelator_8
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_8
ListExploder_8
    INDEX_ATTR = _element_index
    ATTR_CONFLICT_RES = Use Incoming List
    ATTR_ACCUM_MODE = Merge Incoming List
    LIST_ATTR = _relationships{}
    ELEMENTS -> StringConcatenator_9
SpatialRelator_3
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_3
ListExploder_3
    INDEX_ATTR = _element_index
    ATTR_CONFLICT_RES = Use Incoming List
    ATTR_ACCUM_MODE = Merge Incoming List
    LIST_ATTR = _relationships{}
    ELEMENTS -> StringConcatenator_3
SpatialRelator_10
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_10
ListExploder_10
    INDEX_ATTR = _element_index
    ATTR_CONFLICT_RES = Use Incoming List
    ATTR_ACCUM_MODE = Merge Incoming List
    LIST_ATTR = _relationships{}
    ELEMENTS -> StringConcatenator_11
SpatialRelator_11
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_11
ListExploder_11
    INDEX_ATTR = _element_index
    ATTR_CONFLICT_RES = Use Incoming List
    ATTR_ACCUM_MODE = Merge Incoming List
    LIST_ATTR = _relationships{}
    ELEMENTS -> StringConcatenator_12
SpatialRelator_12
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_12
ListExploder_12
    INDEX_ATTR = _element_index
    ATTR_CONFLICT_RES = Use Incoming List
    ATTR_ACCUM_MODE = Merge Incoming List
    LIST_ATTR = _relationships{}
    ELEMENTS -> StringConcatenator_13
SpatialRelator_13
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_13
ListExploder_13
    INDEX_ATTR = _element_index
    ATTR_CONFLICT_RES = Use Incoming List
    ATTR_ACCUM_MODE = Merge Incoming List
    LIST_ATTR = _relationships{}
    ELEMENTS -> StringConcatenator_14
SpatialRelator_9 [off]
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_9 [off]
ListExploder_9 [off]
    INDEX_ATTR = _element_index
    ATTR_CONFLICT_RES = Use Incoming List
    ATTR_ACCUM_MODE = Merge Incoming List
    LIST_ATTR = _relationships{}
    ELEMENTS -> StringConcatenator_10 [off]
SpatialRelator_14
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_14
ListExploder_14
    INDEX_ATTR = _element_index
    ATTR_CONFLICT_RES = Use Incoming List
    ATTR_ACCUM_MODE = Merge Incoming List
    LIST_ATTR = _relationships{}
    ELEMENTS -> StringConcatenator_15
SpatialRelator_15
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_15
ListExploder_15
    INDEX_ATTR = _element_index
    ATTR_CONFLICT_RES = Use Incoming List
    ATTR_ACCUM_MODE = Merge Incoming List
    LIST_ATTR = _relationships{}
    ELEMENTS -> StringConcatenator_16
SpatialRelator
    CURVE_BOUNDARY_RULE_PARAM = Default Rule
    CALC_CARD = No
    LIST_NAME = _relationships
    SUCCESS_ATTR = _related_candidates
    AGGREGATE_HANDLING = Yes
    PREDICATES = CONTAINS INTERSECTS
    -> ListExploder
ListExploder
    INDEX_ATTR = _element_index
    ATTR_CONFLICT_RES = Use Incoming List
    ATTR_ACCUM_MODE = Merge Incoming List
    LIST_ATTR = _relationships{}
    ELEMENTS -> StringConcatenator_4
SpatialRelator_16
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_16
ListExploder_16
    INDEX_ATTR = _element_index
    ATTR_CONFLICT_RES = Use Incoming List
    ATTR_ACCUM_MODE = Merge Incoming List
    LIST_ATTR = _relationships{}
    ELEMENTS -> StringConcatenator_17
SpatialRelator_17
    CURVE_BOUNDARY_RULE_PARAM = Default Rule
    CALC_CARD = No
    LIST_NAME = _relationships
    SUCCESS_ATTR = _related_candidates
    AGGREGATE_HANDLING = Yes
    PREDICATES = CONTAINS INTERSECTS
    -> ListExploder_17
ListExploder_17
    INDEX_ATTR = _element_index
    ATTR_CONFLICT_RES = Use Incoming List
    ATTR_ACCUM_MODE = Merge Incoming List
    LIST_ATTR = _relationships{}
    ELEMENTS -> StringConcatenator_18

Bookmark: Bestandsnaam shapefiles
StringConcatenator_2
    ACTION = Overwrite Existing Attributes
    ATTRLIST = bestandsnaam
    PARM_LINE = @Value(bestandsnaam)
    -> imgeo_extractie.vw_imgeo_kunstwerkdeel_point (writer ESRISHAPE_1)
StringConcatenator_5
    ACTION = Overwrite Existing Attributes
    ATTRLIST = bestandsnaam
    PARM_LINE = @Value(bestandsnaam)
    -> imgeo_extractie.vw_imgeo_kunstwerkdeel_line (writer ESRISHAPE_1)
StringConcatenator_6
    ACTION = Overwrite Existing Attributes
    ATTRLIST = bestandsnaam
    PARM_LINE = @Value(bestandsnaam)
    -> imgeo_extractie.vw_imgeo_kunstwerkdeel_polygon (writer ESRISHAPE_1)
StringConcatenator_7
    ACTION = Overwrite Existing Attributes
    ATTRLIST = bestandsnaam
    PARM_LINE = @Value(bestandsnaam)
    -> imgeo_extractie.vw_imgeo_spoor00 (writer ESRISHAPE_1)
StringConcatenator_8
    ACTION = Overwrite Existing Attributes
    ATTRLIST = bestandsnaam
    PARM_LINE = @Value(bestandsnaam)
    -> imgeo_extractie.vw_imgeo_spoor0000 (writer ESRISHAPE_1)
StringConcatenator_9
    ACTION = Overwrite Existing Attributes
    ATTRLIST = bestandsnaam
    PARM_LINE = @Value(bestandsnaam)
    -> Shapefile1010000 (writer ESRISHAPE_2)
StringConcatenator_3
    ACTION = Overwrite Existing Attributes
    ATTRLIST = bestandsnaam
    PARM_LINE = @Value(bestandsnaam)
    -> Shapefile101000000 (writer ESRISHAPE_2)
StringConcatenator_11
    ACTION = Overwrite Existing Attributes
    ATTRLIST = bestandsnaam
    PARM_LINE = @Value(bestandsnaam)
    -> Shapefile1010001 (writer ESRISHAPE_2)
StringConcatenator_12
    ACTION = Overwrite Existing Attributes
    ATTRLIST = bestandsnaam
    PARM_LINE = @Value(bestandsnaam)
    -> Shapefile1010002 (writer ESRISHAPE_2)
StringConcatenator_13
    ACTION = Overwrite Existing Attributes
    ATTRLIST = bestandsnaam
    PARM_LINE = @Value(bestandsnaam)
    -> Shapefile1010003 (writer ESRISHAPE_2)
StringConcatenator_14
    ACTION = Overwrite Existing Attributes
    ATTRLIST = bestandsnaam
    PARM_LINE = @Value(bestandsnaam)
    -> Shapefile101000300 (writer ESRISHAPE_2)
StringConcatenator_10 [off]
    ACTION = Overwrite Existing Attributes
    ATTRLIST = bestandnaam
    PARM_LINE = @Value(bestandnaam)
    -> imgeo_extractie.vw_imgeo_spoor00000000 (writer ESRISHAPE_1) [off]
StringConcatenator_15
    ACTION = Overwrite Existing Attributes
    ATTRLIST = bestandsnaam
    PARM_LINE = @Value(bestandsnaam)
    -> Shapefile10100 (writer ESRISHAPE_2)
StringConcatenator_16
    ACTION = Overwrite Existing Attributes
    ATTRLIST = bestandsnaam
    PARM_LINE = @Value(bestandsnaam)
    -> Shapefile101 (writer ESRISHAPE_2)
StringConcatenator_4
    ACTION = Overwrite Existing Attributes
    ATTRLIST = bestandsnaam
    PARM_LINE = @Value(bestandsnaam)
    -> Shapefile1 (writer ESRISHAPE_2)
StringConcatenator_17
    ACTION = Overwrite Existing Attributes
    ATTRLIST = bestandsnaam
    PARM_LINE = @Value(bestandsnaam)
    -> Shapefile100 (writer ESRISHAPE_2)
StringConcatenator_18
    ACTION = Overwrite Existing Attributes
    ATTRLIST = bestandsnaam
    PARM_LINE = @Value(bestandsnaam)
    -> Shapefile10000 (writer ESRISHAPE_2)

Bookmark: Totaalgebied shapefiles
Note: lijnen
Note: punten
Note: vlakken
