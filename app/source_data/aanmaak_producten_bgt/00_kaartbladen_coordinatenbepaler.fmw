FME workspace 00_kaartbladen_coordinatenbepaler.fmw

Parameters:
- SourceDataset_POSTGIS_3 = bgt_dev_local   # Connection
- DestDataset_CSV = $(FME_MF_DIR)resource   # Destination CSV (CommaSeparatedValue) Folder

Readers:
- POSTGIS_1: POSTGIS from $(SourceDataset_POSTGIS_3)

Writers:
- CSV_1: CSV to $(DestDataset_CSV) in EPSG:28992

Note: BGT_EXTRACTIE.PDT_KAARTBLAD: bgt_dev [POSTGRES]
imgeo.pdt_kaartblad (reader POSTGIS_1)
    attributes: id serial,PRIKEY, naam varchar(200), big_id int4
    -> AttributeFilter
Note: alleen de kaartbladen, niet de gebieden door
AttributeFilter
    ATTR_NAME = big_id
    ATTR_VALUES = <EMPTY>,<MISSING>,<NULL>,<UNFILTERED>,1
    1 -> BoundsExtractor
Note: hoekpunten eruithalen
BoundsExtractor
    YMAX = ENVELOPE_MAXY
    XMIN = ENVELOPE_MINX
    XMAX = ENVELOPE_MAXX
    ZMAX = _zmax
    YMIN = ENVELOPE_MINY
    ZMIN = _zmin
    -> AttributeRounder
Note: Alles afronden op hele getallen
AttributeRounder
    ROUND_TYPE = nearest
    PLACES = 0
    SRC_ATTRS = ENVELOPE_MINY,ENVELOPE_MAXY,ENVELOPE_MAXX,ENVELOPE_MINX
    -> Kaartbladen_coordinaten (writer CSV_1)
Kaartbladen_coordinaten (writer CSV_1)
    attributes: ENVELOPE_MINX auto, ENVELOPE_MINY auto, ENVELOPE_MAXX auto, ENVELOPE_MAXY auto
