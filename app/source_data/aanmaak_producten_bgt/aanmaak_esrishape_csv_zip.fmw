FME workspace aanmaak_esrishape_csv_zip.fmw
Title: BGT producten
Description: Frietsnijder shapefiles

Parameters:
- SourceDataset_POSTGIS = bgt_dev_local   # Connection
- DestDataset_ESRISHAPE2 = C:\BGT\FME\Esri_Shape\Esri_Shape_gebied   # Destination Esri Shapefolder
- DestDataset_ESRISHAPE3 = C:\BGT\FME\Esri_Shape\Esri_Shape_totaal   # Destination Esri Shapefolder
- SourceDataset_POSTGIS_5 = bgt_dev_local   # Connection
- DestDataset_CSV = C:\BGT\FME\ASCII\ASCII_gebied   # Destination CSV (CommaSeparatedValue) Folder
- DestDataset_CSV_3 = C:\BGT\FME\ASCII\ASCII_totaal   # Destination CSV (CommaSeparatedValue) Folder
- bgt_view = imgeo_extractie.vw_bag_standplaats

Readers:
- POSTGIS_1: POSTGIS from $(SourceDataset_POSTGIS) in EPSG:28992
- POSTGIS_2: POSTGIS from $(SourceDataset_POSTGIS_5) in EPSG:28992

Writers:
- ESRISHAPE_1: ESRISHAPE to $(DestDataset_ESRISHAPE2) in EPSG:28992
- ESRISHAPE_2: ESRISHAPE to $(DestDataset_ESRISHAPE3) in EPSG:28992
- CSV_1: CSV to $(DestDataset_CSV) in EPSG:28992
- CSV_2: CSV to $(DestDataset_CSV_3)

Note: NB BGT object reader: Feature to read -> Feature types to read is voor de fme-cloud gelinkt aan een parameter ivm het draaien van het script per object. / Voor lokaal draaien van het script moet deze link worden uitgezet (unlink en alles lezen)
imgeo_extractie.vw_bgt_pand (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bestandsnaam text, bagpndid varchar(20)
    -> AttributeManager_99
AttributeManager_99
    ATTR_TABLE = RENAME_SET_VALUE einddtijd > eindtijd
    -> Shapefile10000000100000000 (writer ESRISHAPE_2)
    -> PartCounter
    -> SpatialRelator_2 [input 1]
Note: Pand: shp_totaal [ESRISHAPE] - 1
Shapefile10000000100000000 (writer ESRISHAPE_2)
    attributes: namespace char(8), lokaalid char(38), begintijd date, eindtijd date, tijdreg char(20), eindreg char(20), lv_pubdat char(20), bronhoud char(40), inonderzk char(1), hoogtelig short, bgtstatus char(8), plusstatus char(8), bagpndid char(20)
AttributeManager_57
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bagpndid > identificatieBAGPND
    -> imgeo_extractie.vw_bgt_waterdeel0004 (writer CSV_2)
Note: Pand: csv_totaal [CSV]
imgeo_extractie.vw_bgt_waterdeel0004 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, identificatieBAGPND auto, geometrie float
imgeo_extractie.vw_lps_nummeraanduiding (reader POSTGIS_2)
    attributes: bagid varchar(18), bestandsnaam varchar(40), adres text, tekst varchar(10), hoek int2
    -> AttributeManager_115
imgeo_extractie.vw_bgt_ondersteunendwaterdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200)
    -> AttributeManager_107
AttributeManager_107
    ATTR_TABLE = RENAME_SET_VALUE einddtijd > eindtijd
    -> GeometryExtractor_33
    -> Shapefile100000001000000000000000000000100 (writer ESRISHAPE_2)
    -> SpatialRelator_2 [input 1]
Note: Ondersteund.waterdeel: shp_totaal [ESRISHAPE]
Shapefile100000001000000000000000000000100 (writer ESRISHAPE_2)
    attributes: namespace char(8), lokaalid char(38), begintijd date, eindtijd char(200), tijdreg char(20), eindreg char(20), lv_pubdat char(20), bronhoud char(40), inonderzk char(1), hoogtelig short, bgtstatus char(8), plusstatus char(8), bgttype char(200), plustype char(200)
GeometryExtractor_33
    ATTR = geometrie
    KIND_LONG = OGC Well Known Text
    OGCVERSION = 1.1
    OGC_WKT_PRECISION_DISPLAY = Shortened 64-bit
    REMOVE_GEOMETRY = No
    -> AttributeManager_79
AttributeManager_79
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
    -> imgeo_extractie.vw_bgt_waterdeel0013 (writer CSV_2)
Note: Ondersteunend.waterdeel: csv_totaal [CSV]
imgeo_extractie.vw_bgt_waterdeel0013 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgttype text, plustype text, geometrie float
imgeo_extractie.vw_bgt_waterdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), bgttype varchar(200), bestandsnaam text, plusstatus varchar(8), plustype varchar(200)
    -> AttributeManager_108
AttributeManager_108
    ATTR_TABLE = RENAME_SET_VALUE einddtijd > eindtijd
    -> GeometryExtractor_34
    -> Shapefile10000000100000000000000000000010000 (writer ESRISHAPE_2)
    -> SpatialRelator_2 [input 1]
Note: Waterdeel: shp_totaal [ESRISHAPE]
Shapefile10000000100000000000000000000010000 (writer ESRISHAPE_2)
    attributes: namespace char(8), lokaalid char(38), begintijd date, eindtijd date, tijdreg char(20), eindreg char(20), lv_pubdat char(20), bronhoud char(40), inonderzk char(1), hoogtelig short, bgtstatus char(8), plusstatus char(8), bgttype char(200), plustype char(200)
GeometryExtractor_34
    ATTR = geometrie
    KIND_LONG = OGC Well Known Text
    OGCVERSION = 1.1
    OGC_WKT_PRECISION_DISPLAY = Shortened 64-bit
    REMOVE_GEOMETRY = No
    -> AttributeManager_82
AttributeManager_82
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
    -> imgeo_extractie.vw_bgt_waterdeel0014 (writer CSV_2)
Note: Waterdeel: csv_totaal [CSV]
imgeo_extractie.vw_bgt_waterdeel0014 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgttype text, plustype text, geometrie float
imgeo_extractie.vw_bgt_wegdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfunctie varchar(200), bestandsnaam text, bgtfysvkn varchar(200), optalud varchar(1), plusfunct varchar(200), plusfysvkn varchar(200)
    -> AttributeManager_104
AttributeManager_104
    ATTR_TABLE = RENAME_SET_VALUE einddtijd > eindtijd
    -> Shapefile10000000100000000000000000000 (writer ESRISHAPE_2)
    -> GeometryExtractor_30
    -> SpatialRelator_2 [input 1]
Shapefile10000000100000000000000000000 (writer ESRISHAPE_2)
    attributes: namespace char(8), lokaalid char(38), begintijd date, eindtijd date, tijdreg char(20), eindreg char(20), lv_pubdat char(20), bronhoud char(40), inonderzk char(1), hoogtelig short, bgtstatus char(8), plusstatus char(8), bgtfunctie char(200), bgtfysvkn char(200), optalud char(1), plusfunct char(200), plusfysvkn char(200)
GeometryExtractor_30
    ATTR = geometrie
    KIND_LONG = OGC Well Known Text
    OGCVERSION = 1.1
    OGC_WKT_PRECISION_DISPLAY = Shortened 64-bit
    REMOVE_GEOMETRY = No
    -> AttributeManager_84
AttributeManager_84
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfunctie > bgt-functie
      RENAME_SET_VALUE bgtfysvkn > bgt-fysiekvoorkomen
      RENAME_SET_VALUE plusfunct > plus-functie
      RENAME_SET_VALUE plusfysvkn > plus-fysiekvoorkomen
    -> imgeo_extractie.vw_bgt_waterdeel000900 (writer CSV_2)
imgeo_extractie.vw_bgt_waterdeel000900 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-functie auto, bgt-fysiekvoorkomen auto, optalud char(1), plus-functie auto, plus-fysiekvoorkomen auto, geometrie float
imgeo_extractie.vw_bgt_begroeidterreindeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfysvkn varchar(200), bestandsnaam text, optalud varchar(1), plusfysvkn varchar(200)
    -> AttributeManager_105
AttributeManager_105
    ATTR_TABLE = RENAME_SET_VALUE einddtijd > eindtijd
    -> Shapefile1000000010000000000000000000000 (writer ESRISHAPE_2)
    -> GeometryExtractor_31
    -> SpatialRelator_2 [input 1]
Note: Begroeidterrein: shp_totaal [ESRISHAPE]
Shapefile1000000010000000000000000000000 (writer ESRISHAPE_2)
    attributes: namespace char(8), lokaalid char(38), begintijd date, eindtijd date, tijdreg char(20), eindreg char(20), lv_pubdat char(20), bronhoud char(40), inonderzk char(1), hoogtelig short, bgtstatus char(8), plusstatus char(8), bgtfysvkn char(200), optalud char(1), plusfysvkn char(200)
GeometryExtractor_31
    ATTR = geometrie
    KIND_LONG = OGC Well Known Text
    OGCVERSION = 1.1
    OGC_WKT_PRECISION_DISPLAY = Shortened 64-bit
    REMOVE_GEOMETRY = No
    -> AttributeManager_76
AttributeManager_76
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfysvkn > bgt-fysiekvoorkomen
      RENAME_SET_VALUE plusfysvkn > plus-fysiekvoorkomen
    -> imgeo_extractie.vw_bgt_waterdeel00090000 (writer CSV_2)
Note: Begroeidterrein: csv_totaal [CSV]
imgeo_extractie.vw_bgt_waterdeel00090000 (writer CSV_2)
    attributes: identificatie_namespace auto, identificatie_lokaalid auto, objectbegintijd auto, eindregistratie auto, tijdstipregistratie auto, lv-publicatiedatum auto, bronhouder auto, inonderzoek auto, relatievehoogteligging auto, bgt-status auto, plus-status auto, bgt-fysiekvoorkomen auto, optalud char(1), plus-fysiekvoorkomen auto, geometrie float
imgeo_extractie.vw_bgt_onbegroeidterreindeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfysvkn varchar(200), bestandsnaam text, optalud varchar(1), plusfysvkn varchar(200)
    -> AttributeManager_106
AttributeManager_106
    ATTR_TABLE = RENAME_SET_VALUE einddtijd > eindtijd
    -> Shapefile1000000010000000000000000000001 (writer ESRISHAPE_2)
    -> GeometryExtractor_32
    -> SpatialRelator_2 [input 1]
Note: Onbegroeidterrein: shp_totaal [ESRISHAPE]
Shapefile1000000010000000000000000000001 (writer ESRISHAPE_2)
    attributes: namespace char(8), lokaalid char(38), begintijd date, eindtijd date, tijdreg char(20), eindreg char(20), lv_pubdat char(20), bronhoud char(40), inonderzk char(1), hoogtelig short, bgtstatus char(8), plusstatus char(8), bgtfysvkn char(200), optalud char(1), plusfysvkn char(200)
GeometryExtractor_32
    ATTR = geometrie
    KIND_LONG = OGC Well Known Text
    OGCVERSION = 1.1
    OGC_WKT_PRECISION_DISPLAY = Shortened 64-bit
    REMOVE_GEOMETRY = No
    -> AttributeManager_80
AttributeManager_80
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfysvkn > bgt-fysiekvoorkomen
      RENAME_SET_VALUE plusfysvkn > plus-functie
    -> imgeo_extractie.vw_bgt_waterdeel0009000000 (writer CSV_2)
Note: Onbegroeidterrein: csv_totaal [CSV]
imgeo_extractie.vw_bgt_waterdeel0009000000 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-fysiekvoorkomen auto, optalud char(1), plus-functie auto, geometrie float
imgeo_extractie.vw_bgt_ondersteunendwegdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfunctie varchar(200), bestandsnaam text, bgtfysvkn varchar(200), optalud varchar(1), plusfunct varchar(200), plusfysvkn varchar(200)
    -> AttributeManager_103
AttributeManager_103
    -> Shapefile100000001000000000000000000 (writer ESRISHAPE_2)
    -> GeometryExtractor_29
    -> SpatialRelator_2 [input 1]
Note: Wegdeel: shp_totaal [ESRISHAPE]
Shapefile100000001000000000000000000 (writer ESRISHAPE_2)
    attributes: namespace char(8), lokaalid char(38), begintijd date, einddtijd date, tijdreg char(20), eindreg char(20), lv_pubdat char(20), bronhoud char(40), inonderzk char(1), hoogtelig short, bgtstatus char(8), plusstatus char(8), bgtfunctie char(200), bgtfysvkn char(200), optalud char(1), plusfunct char(200), plusfysvkn char(200)
GeometryExtractor_29
    ATTR = geometrie
    KIND_LONG = OGC Well Known Text
    OGCVERSION = 1.1
    OGC_WKT_PRECISION_DISPLAY = Shortened 64-bit
    REMOVE_GEOMETRY = No
    -> AttributeManager_73
AttributeManager_73
    ATTR_TABLE:
      RENAME_SET_VALUE namespace > identificatie_namespace
      RENAME_SET_VALUE lokaalid > identificatie_lokaalid
      RENAME_SET_VALUE begintijd > objectbegintijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE einddtijd > objecteindtijd
      RENAME_SET_VALUE bgtfunctie > bgt-functie
      RENAME_SET_VALUE bgtfysvkn > bgt-fysiekvoorkomen
      RENAME_SET_VALUE plusfunct > plus-functie
      RENAME_SET_VALUE plusfysvkn > plus-fysiekvoorkomen
    -> imgeo_extractie.vw_bgt_waterdeel0009 (writer CSV_2)
Note: Wegdeel: csv_totaal [CSV]
imgeo_extractie.vw_bgt_waterdeel0009 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-functie auto, bgt-fysiekvoorkomen auto, optalud char(1), plus-functie auto, plus-fysiekvoorkomen auto, geometrie float
imgeo_extractie.vw_bgt_kruinlijn (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), optalud varchar(1), bestandsnaam text, hoortbij varchar(200)
    -> AttributeManager_100
AttributeManager_100
    ATTR_TABLE:
      RENAME_SET_VALUE einddtijd > eindtijd
      SET_TO bestandsnaam = BGT_KLN_kruinlijn
    -> GeometryExtractor_25
    -> AttributeManager_37
    -> SpatialRelator_2 [input 1]
GeometryExtractor_25
    ATTR = geometrie
    KIND_LONG = OGC Well Known Text
    OGCVERSION = 1.1
    OGC_WKT_PRECISION_DISPLAY = Shortened 64-bit
    REMOVE_GEOMETRY = No
    -> AttributeManager_59
AttributeManager_59
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
    -> imgeo_extractie.vw_bgt_waterdeel0005 (writer CSV_2)
Note: Kruinlijn: csv_totaal [CSV]
imgeo_extractie.vw_bgt_waterdeel0005 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, optalud char(1), hoortbij text, geometrie float
Note: hoortbij rename to bij_object
AttributeManager_37
    ATTR_TABLE = RENAME_SET_VALUE hoortbij > bij_object
    -> Shapefile1000000010000000000 (writer ESRISHAPE_2)
Note: Kruinlijn: shp_totaal [ESRISHAPE]
Shapefile1000000010000000000 (writer ESRISHAPE_2)
    attributes: namespace char(200), lokaalid char(38), begintijd date, eindtijd char(200), tijdreg char(20), eindreg char(20), lv_pubdat char(20), bronhoud char(40), inonderzk char(1), hoogtelig short, bgtstatus char(8), plusstatus char(8), optalud char(1), bij_object char(200)
imgeo_extractie.vw_bgt_ongeclassificeerdobject (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bestandsnaam text
    -> AttributeManager_98
AttributeManager_98
    ATTR_TABLE = RENAME_SET_VALUE einddtijd > eindtijd
    -> Shapefile100000001000000 (writer ESRISHAPE_2)
    -> GeometryExtractor_23
    -> SpatialRelator_2 [input 1]
GeometryExtractor_23
    ATTR = geometrie
    KIND_LONG = OGC Well Known Text
    OGCVERSION = 1.1
    OGC_WKT_PRECISION_DISPLAY = Shortened 64-bit
    REMOVE_GEOMETRY = No
    -> AttributeManager_55
AttributeManager_55
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
    -> imgeo_extractie.vw_bgt_waterdeel0003 (writer CSV_2)
Note: Ongeclass.: csv_totaal [CSV]
imgeo_extractie.vw_bgt_waterdeel0003 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, geometrie float
Note: Ongeclass.: shp_totaal [ESRISHAPE] - 1
Shapefile100000001000000 (writer ESRISHAPE_2)
    attributes: namespace char(8), lokaalid char(38), begintijd date, eindtijd date, tijdreg char(20), eindreg char(20), lv_pubdat char(20), bronhoud char(40), inonderzk char(1), hoogtelig short, bgtstatus char(8), plusstatus char(8)
imgeo_extractie.vw_bgt_tunneldeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bestandsnaam text
    -> AttributeManager_95
AttributeManager_95
    ATTR_TABLE = RENAME_SET_VALUE einddtijd > eindtijd
    -> Shapefile100000001 (writer ESRISHAPE_2)
    -> GeometryExtractor_20
    -> SpatialRelator_2 [input 1]
GeometryExtractor_20
    ATTR = geometrie
    KIND_LONG = OGC Well Known Text
    OGCVERSION = 1.1
    OGC_WKT_PRECISION_DISPLAY = Shortened 64-bit
    REMOVE_GEOMETRY = No
    -> AttributeManager_49
AttributeManager_49
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
    -> imgeo_extractie.vw_bgt_waterdeel0000 (writer CSV_2)
Note: Tunneldeel: csv_totaal [CSV]
imgeo_extractie.vw_bgt_waterdeel0000 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, geometrie float
Note: Tunneldeel: shp_totaal [ESRISHAPE]
Shapefile100000001 (writer ESRISHAPE_2)
    attributes: namespace char(8), lokaalid char(38), begintijd date, eindtijd date, tijdreg char(20), eindreg char(20), lv_pubdat char(20), bronhoud char(40), inonderzk char(1), hoogtelig short, bgtstatus char(8), plusstatus char(8)
imgeo_extractie.vw_imgeo_spoor (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgtfunctie varchar(200), bestandsnaam text, plusfunct varchar(200), bestandsnaam_plus text
    -> AttributeManager_13
AttributeManager_13
    ATTR_TABLE:
      RENAME_SET_VALUE einddtijd > eindtijd
      SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
      REMOVE bestandsnaam_plus
    -> GeometryExtractor_21
    -> Shapefile10000000100 (writer ESRISHAPE_2)
    -> SpatialRelator_2 [input 1]
GeometryExtractor_21
    ATTR = geometrie
    KIND_LONG = OGC Well Known Text
    OGCVERSION = 1.1
    OGC_WKT_PRECISION_DISPLAY = Shortened 64-bit
    REMOVE_GEOMETRY = No
    -> AttributeManager_51
AttributeManager_51
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfunctie > bgt-functie
      RENAME_SET_VALUE plusfunct > plus-functie
    -> imgeo_extractie.vw_bgt_waterdeel0001 (writer CSV_2)
Note: Spoor: csv_totaal [CSV]
imgeo_extractie.vw_bgt_waterdeel0001 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-functie auto, plus-functie auto, geometrie float
Note: Spoor: shp_totaal [ESRISHAPE] - 1
Shapefile10000000100 (writer ESRISHAPE_2)
    attributes: namespace char(8), lokaalid char(38), begintijd date, eindtijd date, tijdreg char(20), eindreg char(20), lv_pubdat char(20), bronhoud char(40), inonderzk char(1), hoogtelig short, bgtstatus char(8), plusstatus char(8), bgtfunctie char(200), plusfunct char(200)
SpatialRelator_2
    CURVE_BOUNDARY_RULE_PARAM = Default Rule
    SUCCESS_ATTR = _related_candidates
    AGGREGATE_HANDLING = Yes
    PREDICATES = INTERSECTS CONTAINS
    CALC_CARD = No
    LIST_NAME = _relationships
    -> ListExploder_2
Note: uitsplitsen Overbruggingsdeel per object
AttributeFilter_3
    ATTR_NAME = type
    ATTR_VALUES = <EMPTY>,<MISSING>,<NULL>,<UNFILTERED>,pijler,pyloon,dek,landhoofd,sloof
    pijler -> GeometryExtractor_39
    pijler -> imgeo_extractie.vw_imgeo_kunstwerkdeel_point0100000000 (writer ESRISHAPE_1)
    pyloon -> GeometryExtractor_49
    pyloon -> imgeo_extractie.vw_imgeo_kunstwerkdeel_point010000000001 (writer ESRISHAPE_1)
    dek -> GeometryExtractor_51
    dek -> imgeo_extractie.vw_imgeo_kunstwerkdeel_point01000000000100 (writer ESRISHAPE_1)
    landhoofd -> GeometryExtractor_53
    sloof -> GeometryExtractor_55
    sloof -> imgeo_extractie.vw_imgeo_kunstwerkdeel_point010000000001000000 (writer ESRISHAPE_1)
    <UNFILTERED> -> GeometryExtractor_57
    <UNFILTERED> -> imgeo_extractie.vw_imgeo_kunstwerkdeel_point01000000000100000000 (writer ESRISHAPE_1)
    landhoofd -> imgeo_extractie.vw_imgeo_kunstwerkdeel_point0100000000010000 (writer ESRISHAPE_1)
GeometryExtractor_51
    ATTR = geometrie
    KIND_LONG = OGC Well Known Text
    OGCVERSION = 1.1
    OGC_WKT_PRECISION_DISPLAY = Shortened 64-bit
    REMOVE_GEOMETRY = No
    -> AttributeManager_88

Bookmark: Bepalen multi polygone en polygon
Note: Tel delen van pand
PartCounter
    RECURSIVE_PARAM = No
    COUNT_ATTR = _part_count
    -> Tester
Note: Bepalen panden die bestaan uit 1 deel (part) dit zijn de ploygons / anders zijn dit pandenmet meerdere delen (multipolygons0
Tester
    TEST_MODE = Automatic
    TEST_CLAUSE = TEST @Value(_part_count) = 1
    TEST_DESCRIPTION = ""
    BOOL_OP = OR
    PASSED -> Deaggregator
    FAILED -> GeometryExtractor_24
Deaggregator
    CHILD_ID_ATTR = _hierarchy_child_id_list
    GEOM_NAME_FIELD = _geometry_name
    ID_ATTR = _hierarchy_id
    PARENT_ID_ATTR = _hierarchy_parent_id
    EXPLODE_INSTANCES = No
    LIST_ATTR_MODE_LOOKUP = LEAN
    COPY_ATTR = Every Node
    ID_SELECTION = ID and Parent ID
    MODE = Flatten One Level
    SPLIT_COMPOSITES = No
    PART_NUMBER_FIELD = _part_number
    DEAGGREGATED -> GeometryExtractor_24
GeometryExtractor_24
    ATTR = geometrie
    KIND_LONG = OGC Well Known Text
    OGCVERSION = 1.1
    OGC_WKT_PRECISION_DISPLAY = Shortened 64-bit
    REMOVE_GEOMETRY = No
    -> AttributeManager_57

Bookmark: Comfortinformatie: Over- en Onderbouw en BAG: stand- en ligplaatsen
Note: Bepalen labelhoek ivm Qgis (360-hoek)
AttributeManager_115
    ATTR_TABLE = SET_TO hoek = FME_CONDITIONAL:DEFAULT_VALUE'@Evaluate((-1*@Value(hoek))+360)'BOOL_OP;OR;COMPOSITE_TEST;<Unused>;TEST @Value(hoek) RANGE (180,360)'@Evaluate(360-@Value(hoek))'FME_NUM_CONDITIONS2___
    -> bestandsnaam0000 (writer ESRISHAPE_2)
    -> GeometryExtractor_58
    -> SpatialRelator_2 [input 1]
Note: lps-nraanduiding: shp_totaal [ESRISHAPE]
bestandsnaam0000 (writer ESRISHAPE_2)
    attributes: bagid char(20), adres char(254), tekst char(10), hoek float
GeometryExtractor_58
    ATTR = geometrie
    KIND_LONG = OGC Well Known Text
    OGCVERSION = 1.1
    OGC_WKT_PRECISION_DISPLAY = Shortened 64-bit
    REMOVE_GEOMETRY = No
    -> AttributeManager_114
AttributeManager_114
    ATTR_TABLE:
      RENAME_SET_VALUE bagid > BAG_identificatie
      REMOVE fme_feature_type
    -> imgeo_extractie.vw_imgeo_scheiding000100000000 (writer CSV_2)
Note: lbl_Ligplaats: csv_totaal [CSV]
imgeo_extractie.vw_imgeo_scheiding000100000000 (writer CSV_2)
    attributes: BAG_identificatie auto, adres text, tekst text, hoek float, geometrie auto
imgeo_extractie.vw_bag_ligplaats (reader POSTGIS_2)
    attributes: bagid varchar(18), bestandsnaam varchar(15)
    -> imgeo_extractie.vw_imgeo_kunstwerkdeel_polygon000000 (writer ESRISHAPE_2)
    -> GeometryExtractor_6
    -> SpatialRelator_2 [input 1]
Note: BAG_Ligplaats: shp_totaal [ESRISHAPE] - 1
imgeo_extractie.vw_imgeo_kunstwerkdeel_polygon000000 (writer ESRISHAPE_2)
    attributes: bagid char(20)
GeometryExtractor_6
    ATTR = geometrie
    KIND_LONG = OGC Well Known Text
    OGCVERSION = 1.1
    OGC_WKT_PRECISION_DISPLAY = Shortened 64-bit
    REMOVE_GEOMETRY = No
    -> AttributeManager_63
AttributeManager_63
    ATTR_TABLE = RENAME_SET_VALUE bagid > BAG_identificatie
    -> imgeo_extractie.vw_imgeo_scheiding0001000000 (writer CSV_2)
Note: BAG_Ligplaats: csv_totaal [CSV]
imgeo_extractie.vw_imgeo_scheiding0001000000 (writer CSV_2)
    attributes: BAG_identificatie auto, geometrie auto
imgeo_extractie.vw_cft_overbouw (reader POSTGIS_2)
    attributes: eindreg date, hoogtelig int2, bestandsnaam varchar(15), guid varchar(38)
    -> GeometryExtractor_10
    -> Shapefile100000001000000000000000100 (writer ESRISHAPE_2)
    -> SpatialRelator_2 [input 1]
Note: Openbare ruimte: shp_totaal [ESRISHAPE]
Shapefile100000001000000000000000100 (writer ESRISHAPE_2)
    attributes: guid char(38), eindreg char(20), hoogtelig short
GeometryExtractor_10
    ATTR = geometrie
    KIND_LONG = OGC Well Known Text
    OGCVERSION = 1.1
    OGC_WKT_PRECISION_DISPLAY = Shortened 64-bit
    REMOVE_GEOMETRY = No
    -> AttributeManager_65
AttributeManager_65
    ATTR_TABLE:
      RENAME_SET_VALUE eindreg > eindregistratie
      RENAME_SET_VALUE hoogtelig > relatievehoogteligging
      REMOVE fme_feature_type
    -> imgeo_extractie.vw_imgeo_scheiding000100000001 (writer CSV_2)
Note: : ASCII_totaal [CSV]
imgeo_extractie.vw_imgeo_scheiding000100000001 (writer CSV_2)
    attributes: guid auto, eindregistratie char(8), relatievehoogteligging auto, geometrie auto
imgeo_extractie.vw_cft_onderbouw (reader POSTGIS_2)
    attributes: eindreg date, hoogtelig int2, bestandsnaam varchar(15), guid varchar(38)
    -> GeometryExtractor_11
    -> Shapefile1000000010000000000000001 (writer ESRISHAPE_2)
    -> SpatialRelator_2 [input 1]
Note: shp_totaal [ESRISHAPE]
Shapefile1000000010000000000000001 (writer ESRISHAPE_2)
    attributes: guid char(38), eindreg char(20), hoogtelig short
GeometryExtractor_11
    ATTR = geometrie
    KIND_LONG = OGC Well Known Text
    OGCVERSION = 1.1
    OGC_WKT_PRECISION_DISPLAY = Shortened 64-bit
    REMOVE_GEOMETRY = No
    -> AttributeManager_67
AttributeManager_67
    ATTR_TABLE:
      RENAME_SET_VALUE eindreg > eindregistratie
      RENAME_SET_VALUE hoogtelig > relatievehoogteligging
      REMOVE fme_feature_type
    -> imgeo_extractie.vw_imgeo_scheiding00010000000000 (writer CSV_2)
Note: : ASCII_totaal [CSV]
imgeo_extractie.vw_imgeo_scheiding00010000000000 (writer CSV_2)
    attributes: guid auto, eindregistratie char(8), relatievehoogteligging auto, geometrie auto
imgeo_extractie.vw_sps_nummeraanduiding (reader POSTGIS_2)
    attributes: bagid varchar(18), bestandsnaam varchar(40), adres text, tekst varchar(10), hoek int2
    -> bestandsnaam00 (writer ESRISHAPE_2)
    -> GeometryExtractor_60
    -> SpatialRelator_2 [input 1]
GeometryExtractor_60
    ATTR = geometrie
    KIND_LONG = OGC Well Known Text
    OGCVERSION = 1.1
    OGC_WKT_PRECISION_DISPLAY = Shortened 64-bit
    REMOVE_GEOMETRY = No
    -> AttributeManager_116
AttributeManager_116
    ATTR_TABLE:
      RENAME_SET_VALUE bagid > BAG_identificatie
      REMOVE fme_feature_type
    -> imgeo_extractie.vw_imgeo_scheiding0001000001 (writer CSV_2)
Note: sps_nraanduiding: csv_totaal [CSV]
imgeo_extractie.vw_imgeo_scheiding0001000001 (writer CSV_2)
    attributes: BAG_identificatie auto, adres text, tekst text, hoek float, geometrie auto
Note: sps-nraanduiding: shp_totaal [ESRISHAPE]
bestandsnaam00 (writer ESRISHAPE_2)
    attributes: bagid char(20), adres char(254), tekst char(10), hoek float
imgeo_extractie.vw_bag_standplaats (reader POSTGIS_2)
    attributes: bagid varchar(18), bestandsnaam varchar(15)
    -> bestandsnaam (writer ESRISHAPE_2)
    -> GeometryExtractor_5
    -> SpatialRelator_2 [input 1]
Note: BAG_Stanbdplaats: shp_totaal [ESRISHAPE]
bestandsnaam (writer ESRISHAPE_2)
    attributes: bagid char(20)
GeometryExtractor_5
    ATTR = geometrie
    KIND_LONG = OGC Well Known Text
    OGCVERSION = 1.1
    OGC_WKT_PRECISION_DISPLAY = Shortened 64-bit
    REMOVE_GEOMETRY = No
    -> AttributeManager_61
AttributeManager_61
    ATTR_TABLE = RENAME_SET_VALUE bagid > BAG_identificatie
    -> imgeo_extractie.vw_imgeo_scheiding00010000 (writer CSV_2)
Note: BAG_Standplaats: csv_totaal [CSV]
imgeo_extractie.vw_imgeo_scheiding00010000 (writer CSV_2)
    attributes: BAG_identificatie auto, geometrie auto

Bookmark: Overbruggingsdeel
imgeo_extractie.vw_bgt_overbruggingsdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), plustype varchar(200), bestandsnaam text, hoortbij varchar(200), isbeweegb varchar(1)
    -> AttributeManager_97
AttributeManager_97
    ATTR_TABLE:
      RENAME_SET_VALUE einddtijd > eindtijd
      RENAME_SET_VALUE plustype > type
    -> AttributeFilter_2
AttributeFilter_2
    ATTR_NAME = type
    ATTR_VALUES = <EMPTY>,<MISSING>,<NULL>,<UNFILTERED>,pijler,pyloon,dek,landhoofd,sloof
    <UNFILTERED> -> GeometryExtractor_56
    <UNFILTERED> -> Shapefile10000000100000100000000 (writer ESRISHAPE_2)
    <EMPTY> -> Shapefile10000000100000100000000 (writer ESRISHAPE_2)
    <EMPTY> -> GeometryExtractor_56
    <MISSING> -> Shapefile10000000100000100000000 (writer ESRISHAPE_2)
    <MISSING> -> GeometryExtractor_56
    <NULL> -> Shapefile10000000100000100000000 (writer ESRISHAPE_2)
    <NULL> -> GeometryExtractor_56
    pijler -> AttributeManager_96
    pyloon -> AttributeManager_109
    landhoofd -> AttributeManager_110
    sloof -> AttributeManager_111
    dek -> AttributeManager_112
    <NULL> -> SpatialRelator_2 [input 1]
    <EMPTY> -> SpatialRelator_2 [input 1]
    <UNFILTERED> -> SpatialRelator_2 [input 1]
    <MISSING> -> SpatialRelator_2 [input 1]
AttributeManager_96
    ATTR_TABLE = SET_TO bestandsnaam = BGTPLUS_ODL_pijler
    -> GeometryExtractor_22
    -> Shapefile1000000010000 (writer ESRISHAPE_2)
    -> SpatialRelator_2 [input 1]
AttributeManager_109
    ATTR_TABLE = SET_TO bestandsnaam = BGTPLUS_ODL_pyloon
    -> GeometryExtractor_48
    -> Shapefile100000001000001 (writer ESRISHAPE_2)
    -> SpatialRelator_2 [input 1]
AttributeManager_112
    ATTR_TABLE = SET_TO bestandsnaam = BGTPLUS_ODL_dek
    -> GeometryExtractor_50
    -> Shapefile10000000100000100 (writer ESRISHAPE_2)
    -> SpatialRelator_2 [input 1]
AttributeManager_110
    ATTR_TABLE = SET_TO bestandsnaam = BGTPLUS_ODL_landhoofd
    -> GeometryExtractor_52
    -> Shapefile1000000010000010000 (writer ESRISHAPE_2)
    -> SpatialRelator_2 [input 1]
Note: Overbrug.deel: shp_totaal [ESRISHAPE] - 1
AttributeManager_111
    ATTR_TABLE = SET_TO bestandsnaam = BGTPLUS_ODL_sloof
    -> GeometryExtractor_54
    -> Shapefile100000001000001000000 (writer ESRISHAPE_2)
    -> SpatialRelator_2 [input 1]

Bookmark: Overbruggingsdeel: Onbekend of leeg
GeometryExtractor_56
    ATTR = geometrie
    KIND_LONG = OGC Well Known Text
    OGCVERSION = 1.1
    OGC_WKT_PRECISION_DISPLAY = Shortened 64-bit
    REMOVE_GEOMETRY = No
    -> AttributeManager_93
AttributeManager_93
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
      RENAME_SET_VALUE isbeweegb > overbruggingisbeweegbaar
    -> imgeo_extractie.vw_bgt_waterdeel00020000000000 (writer CSV_2)
Note: overbrug.deel: csv_totaal [CSV]
imgeo_extractie.vw_bgt_waterdeel00020000000000 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, type auto, hoortbijtypeoverbrugging auto, overbruggingisbeweegbaar auto, geometrie float
Note: Overbrug.deel: shp_totaal [ESRISHAPE] - 1
Shapefile10000000100000100000000 (writer ESRISHAPE_2)
    attributes: namespace char(8), lokaalid char(38), begintijd date, eindtijd date, tijdreg char(20), eindreg char(20), lv_pubdat char(20), bronhoud char(40), inonderzk char(1), hoogtelig short, bgtstatus char(8), plusstatus char(8), type char(200), hoortbij char(200), isbeweegb char(1)

Bookmark: Overbruggingsdeel: pijler
GeometryExtractor_22
    ATTR = geometrie
    KIND_LONG = OGC Well Known Text
    OGCVERSION = 1.1
    OGC_WKT_PRECISION_DISPLAY = Shortened 64-bit
    REMOVE_GEOMETRY = No
    -> AttributeManager_53
AttributeManager_53
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
      RENAME_SET_VALUE isbeweegb > overbruggingisbeweegbaar
    -> imgeo_extractie.vw_bgt_waterdeel0002 (writer CSV_2)
Note: Overbrug.deel_Pijler: csv_totaal [CSV]
imgeo_extractie.vw_bgt_waterdeel0002 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, type auto, hoortbijtypeoverbrugging auto, overbruggingisbeweegbaar auto, geometrie float
Note: Overbrug.deel_pijler: shp_totaal [ESRISHAPE] - 1
Shapefile1000000010000 (writer ESRISHAPE_2)
    attributes: namespace char(8), lokaalid char(38), begintijd date, eindtijd date, tijdreg char(20), eindreg char(20), lv_pubdat char(20), bronhoud char(40), inonderzk char(1), hoogtelig short, bgtstatus char(8), plusstatus char(8), type char(200), hoortbij char(200), isbeweegb char(1)

Bookmark: Overbruggingsdeel_pyloon
GeometryExtractor_48
    ATTR = geometrie
    KIND_LONG = OGC Well Known Text
    OGCVERSION = 1.1
    OGC_WKT_PRECISION_DISPLAY = Shortened 64-bit
    REMOVE_GEOMETRY = No
    -> AttributeManager_78
AttributeManager_78
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
      RENAME_SET_VALUE isbeweegb > overbruggingisbeweegbaar
    -> imgeo_extractie.vw_bgt_waterdeel000200 (writer CSV_2)
Note: overbrug.deel: csv_totaal [CSV]
imgeo_extractie.vw_bgt_waterdeel000200 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, type auto, hoortbijtypeoverbrugging auto, overbruggingisbeweegbaar auto, geometrie float
Note: Overbrug.deel: shp_totaal [ESRISHAPE] - 1
Shapefile100000001000001 (writer ESRISHAPE_2)
    attributes: namespace char(8), lokaalid char(38), begintijd date, eindtijd date, tijdreg char(20), eindreg char(20), lv_pubdat char(20), bronhoud char(40), inonderzk char(1), hoogtelig short, bgtstatus char(8), plusstatus char(8), type char(200), hoortbij char(200), isbeweegb char(1)

Bookmark: Overbruggingsdeel: dek
Shapefile10000000100000100 (writer ESRISHAPE_2)
    attributes: namespace char(8), lokaalid char(38), begintijd date, eindtijd date, tijdreg char(20), eindreg char(20), lv_pubdat char(20), bronhoud char(40), inonderzk char(1), hoogtelig short, bgtstatus char(8), plusstatus char(8), type char(200), hoortbij char(200), isbeweegb char(1)
GeometryExtractor_50
    ATTR = geometrie
    KIND_LONG = OGC Well Known Text
    OGCVERSION = 1.1
    OGC_WKT_PRECISION_DISPLAY = Shortened 64-bit
    REMOVE_GEOMETRY = No
    -> AttributeManager_87
AttributeManager_87
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
      RENAME_SET_VALUE isbeweegb > overbruggingisbeweegbaar
    -> imgeo_extractie.vw_bgt_waterdeel00020000 (writer CSV_2)
Note: overbrug.deel: csv_totaal [CSV]
imgeo_extractie.vw_bgt_waterdeel00020000 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, type auto, hoortbijtypeoverbrugging auto, overbruggingisbeweegbaar auto, geometrie float

Bookmark: overbruggingsdeel: landshoofd
GeometryExtractor_52
    ATTR = geometrie
    KIND_LONG = OGC Well Known Text
    OGCVERSION = 1.1
    OGC_WKT_PRECISION_DISPLAY = Shortened 64-bit
    REMOVE_GEOMETRY = No
    -> AttributeManager_89
AttributeManager_89
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
      RENAME_SET_VALUE isbeweegb > overbruggingisbeweegbaar
    -> imgeo_extractie.vw_bgt_waterdeel0002000000 (writer CSV_2)
Note: overbrug.deel: csv_totaal [CSV]
imgeo_extractie.vw_bgt_waterdeel0002000000 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, type auto, hoortbijtypeoverbrugging auto, overbruggingisbeweegbaar auto, geometrie float
Note: Overbrug.deel: shp_totaal [ESRISHAPE] - 1
Shapefile1000000010000010000 (writer ESRISHAPE_2)
    attributes: namespace char(8), lokaalid char(38), begintijd date, eindtijd date, tijdreg char(20), eindreg char(20), lv_pubdat char(20), bronhoud char(40), inonderzk char(1), hoogtelig short, bgtstatus char(8), plusstatus char(8), type char(200), hoortbij char(200), isbeweegb char(1)

Bookmark: Overbruggingsdeel: Sloof
GeometryExtractor_54
    ATTR = geometrie
    KIND_LONG = OGC Well Known Text
    OGCVERSION = 1.1
    OGC_WKT_PRECISION_DISPLAY = Shortened 64-bit
    REMOVE_GEOMETRY = No
    -> AttributeManager_91
AttributeManager_91
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
      RENAME_SET_VALUE isbeweegb > overbruggingisbeweegbaar
    -> imgeo_extractie.vw_bgt_waterdeel000200000000 (writer CSV_2)
Note: overbrug.deel: csv_totaal [CSV]
imgeo_extractie.vw_bgt_waterdeel000200000000 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, type auto, hoortbijtypeoverbrugging auto, overbruggingisbeweegbaar auto, geometrie float
Note: Overbrug.deel: shp_totaal [ESRISHAPE] - 1
Shapefile100000001000001000000 (writer ESRISHAPE_2)
    attributes: namespace char(8), lokaalid char(38), begintijd date, eindtijd date, tijdreg char(20), eindreg char(20), lv_pubdat char(20), bronhoud char(40), inonderzk char(1), hoogtelig short, bgtstatus char(8), plusstatus char(8), type char(200), hoortbij char(200), isbeweegb char(1)

Bookmark: Objectklassen tbv de labels voor openbare ruimte en huisnummerreeksen
imgeo_extractie.vw_bgt_openbareruimtelabel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bagoprid varchar(20), oprtype varchar(200), bestandsnaam text, hoek float4, tekst varchar(200)
    -> AttributeManager_101
AttributeManager_101
    -> Shapefile10000000100000000000000 (writer ESRISHAPE_2)
    -> GeometryExtractor_27
    -> SpatialRelator_2 [input 1]
Note: Openbare ruimte: shp_totaal [ESRISHAPE]
Shapefile10000000100000000000000 (writer ESRISHAPE_2)
    attributes: namespace char(8), lokaalid char(38), begintijd date, einddtijd date, tijdreg char(20), eindreg char(20), lv_pubdat char(20), bronhoud char(40), inonderzk char(1), hoogtelig short, bgtstatus char(8), plusstatus char(8), bagoprid char(20), oprtype char(200), hoek float, tekst char(200)
GeometryExtractor_27
    ATTR = geometrie
    KIND_LONG = OGC Well Known Text
    OGCVERSION = 1.1
    OGC_WKT_PRECISION_DISPLAY = Shortened 64-bit
    REMOVE_GEOMETRY = No
    -> AttributeManager_69
AttributeManager_69
    ATTR_TABLE:
      RENAME_SET_VALUE namespace > identificatie_namespace
      RENAME_SET_VALUE lokaalid > identificatie_lokaalid
      RENAME_SET_VALUE begintijd > objectbegintijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE einddtijd > objecteindtijd
      RENAME_SET_VALUE bagoprid > identificatieBAGOPR
      RENAME_SET_VALUE oprtype > openbareruimtetype
    -> imgeo_extractie.vw_bgt_waterdeel0007 (writer CSV_2)
Note: Openbare ruimte: csv_totaal [CSV]
imgeo_extractie.vw_bgt_waterdeel0007 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, identificatieBAGOPR auto, openbareruimtetype auto, tekst text, hoek float, geometrie float
imgeo_extractie.vw_bgt_nummeraanduidingreeks (reader POSTGIS_2)
    attributes: namespace varchar(8), lokaalid varchar(38), begintijd date, tijdreg date, eindreg date, lv_pubdat date, bronhoud varchar(40), inonderzk varchar(1), hoogtelig int2, bgtstatus varchar(8), plusstatus varchar(8), bestandsnaam text, hoek float4, tekst varchar(200), tekst_afk varchar(200), eindtijd date, bagpndid varchar(20), bagvbolgst varchar(20), bagvbohgst varchar(20)
    -> AttributeRounder
AttributeRounder
    SRC_ATTRS = hoek
    ROUND_TYPE = up
    PLACES = 2
    -> AttributeManager_102
AttributeManager_102
    ATTR_TABLE:
      REMOVE namespace
      REMOVE begintijd
      REMOVE tijdreg
      REMOVE eindreg
      REMOVE lv_pubdat
      REMOVE bronhoud
      REMOVE inonderzk
      REMOVE hoogtelig
      REMOVE bgtstatus
      REMOVE plusstatus
      REMOVE eindtijd
    -> GeometryExtractor_28
    -> Shapefile1000000010000000000000000 (writer ESRISHAPE_2)
    -> SpatialRelator_2 [input 1]
Note: Huisnrs: shp_totaal [ESRISHAPE]
Shapefile1000000010000000000000000 (writer ESRISHAPE_2)
    attributes: lokaalid char(38), bagpndid char(20), tekst char(200), tekst_afk char(200), bagvbolgst char(20), bagvbohgst char(20), hoek float
GeometryExtractor_28
    ATTR = geometrie
    KIND_LONG = OGC Well Known Text
    OGCVERSION = 1.1
    OGC_WKT_PRECISION_DISPLAY = Shortened 64-bit
    REMOVE_GEOMETRY = No
    -> AttributeManager_71
AttributeManager_71
    ATTR_TABLE:
      RENAME_SET_VALUE tekst_afk > tekst_afgekort
      RENAME_SET_VALUE bagpndid > identificatieBAGPND
      RENAME_SET_VALUE bagvbolgst > identificatieBAGVBOLaagsteHuisnummer
      RENAME_SET_VALUE bagvbohgst > identificatieBAGVBOHoogsteHuisnummer
      REMOVE fme_feature_type
      RENAME_SET_VALUE lokaalid > identificatie_lokaalid
    -> imgeo_extractie.vw_bgt_waterdeel0008 (writer CSV_2)
Note: Huisnrs: csv_totaal [CSV]
imgeo_extractie.vw_bgt_waterdeel0008 (writer CSV_2)
    attributes: identificatie_lokaalid auto, identificatieBAGPND auto, tekst auto, tekst_afgekort auto, identificatieBAGVBOLaagsteHuisnummer auto, identificatieBAGVBOHoogsteHuisnummer auto, hoek float, geometrie float

Bookmark: Punt-, lijn- en vlakobjectklassen met generieke attributen
imgeo_extractie.vw_imgeo_straatmeubilair (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_14
Note: Data Flow
AttributeManager_14
    ATTR_TABLE:
      RENAME_SET_VALUE einddtijd > eindtijd
      SET_TO bestandsnaam = FME_CONDITIONAL:DEFAULT_VALUE'_FME_NO_OP_'BOOL_OP;AND;COMPOSITE_TEST;<Unused>;TEST bestandsnaam ATTRIBUTE_VALUE_NULL _FME_BLANK_STRING_'@Value(bestandsnaam_plus)'FME_NUM_CONDITIONS2___
      REMOVE bestandsnaam_plus
    -> verzamelaar
imgeo_extractie.vw_imgeo_put (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_12
AttributeManager_12
    ATTR_TABLE:
      RENAME_SET_VALUE einddtijd > eindtijd
      SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
      REMOVE bestandsnaam_plus
    -> verzamelaar
imgeo_extractie.vw_imgeo_mast (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_9
AttributeManager_9
    ATTR_TABLE:
      RENAME_SET_VALUE einddtijd > eindtijd
      SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
      REMOVE bestandsnaam_plus
    -> verzamelaar
imgeo_extractie.vw_imgeo_kast (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager
AttributeManager
    ATTR_TABLE:
      RENAME_SET_VALUE einddtijd > eindtijd
      SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
      REMOVE bestandsnaam_plus
    -> verzamelaar
imgeo_extractie.vw_imgeo_installatie (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_8
AttributeManager_8
    ATTR_TABLE:
      RENAME_SET_VALUE einddtijd > eindtijd
      SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
      REMOVE bestandsnaam_plus
    -> verzamelaar
imgeo_extractie.vw_imgeo_bord (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_5
AttributeManager_5
    ATTR_TABLE:
      RENAME_SET_VALUE einddtijd > eindtijd
      SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
      REMOVE bestandsnaam_plus
    -> verzamelaar
imgeo_extractie.vw_imgeo_bak (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_4
AttributeManager_4
    ATTR_TABLE:
      RENAME_SET_VALUE einddtijd > eindtijd
      SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
      REMOVE bestandsnaam_plus
    -> verzamelaar
imgeo_extractie.vw_imgeo_weginrichtingselement (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_20
AttributeManager_20
    ATTR_TABLE:
      RENAME_SET_VALUE einddtijd > eindtijd
      SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
      REMOVE bestandsnaam_plus
    -> GeometryFilter_8
GeometryFilter_8
    INSTANTIATE = Yes
    GEOM_PORT_NAMES = Point Line Area Surface
    BREAK_AGG = Yes
    POINT -> AttributeManager_34
    LINE -> AttributeManager_35
    AREA -> AttributeManager_36
    SURFACE -> AttributeManager_36
AttributeManager_34
    ATTR_TABLE = SET_TO bestandsnaam = FME_CONDITIONAL:DEFAULT_VALUE'_FME_NO_OP_'BOOL_OP;OR;COMPOSITE_TEST;<Unused>;TEST @Value(bestandsnaam) IN BGTPLUS_WGI_wegmarkering,BGTPLUS_WGI_wildrooster,BGTPLUS_WGI_rooster,BGTPLUS_WGI_geleideconstructie,BGTPLUS_WGI_boomspiegel,BGTPLUS_WGI_onbekend'@Value(bestandsnaam)_P'FME_NUM_CONDITIONS2___
    -> verzamelaar
AttributeManager_35
    ATTR_TABLE = SET_TO bestandsnaam = FME_CONDITIONAL:DEFAULT_VALUE'_FME_NO_OP_'BOOL_OP;OR;COMPOSITE_TEST;<Unused>;TEST @Value(bestandsnaam) IN BGTPLUS_WGI_wegmarkering,BGTPLUS_WGI_wildrooster,BGTPLUS_WGI_rooster,BGTPLUS_WGI_geleideconstructie,BGTPLUS_WGI_boomspiegel,BGTPLUS_WGI_onbekend'@Value(bestandsnaam)_L'FME_NUM_CONDITIONS2___
    -> verzamelaar_2
AttributeManager_36
    ATTR_TABLE = SET_TO bestandsnaam = FME_CONDITIONAL:DEFAULT_VALUE'_FME_NO_OP_'BOOL_OP;OR;COMPOSITE_TEST;<Unused>;TEST @Value(bestandsnaam) IN BGTPLUS_WGI_wegmarkering,BGTPLUS_WGI_wildrooster,BGTPLUS_WGI_rooster,BGTPLUS_WGI_geleideconstructie,BGTPLUS_WGI_boomspiegel,BGTPLUS_WGI_onbekend'@Value(bestandsnaam)_V'FME_NUM_CONDITIONS2___
    -> verzamelaar_4
imgeo_extractie.vw_imgeo_waterinrichtingselement (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_19
AttributeManager_19
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_3
GeometryFilter_3
    INSTANTIATE = Yes
    GEOM_PORT_NAMES = Point Line
    BREAK_AGG = Yes
    POINT -> AttributeManager_32
    LINE -> AttributeManager_33
AttributeManager_32
    ATTR_TABLE = SET_TO bestandsnaam = FME_CONDITIONAL:DEFAULT_VALUE'_FME_NO_OP_'BOOL_OP;OR;COMPOSITE_TEST;<Unused>;TEST @Value(bestandsnaam) = BGTPLUS_WDI_onbekend'@Value(bestandsnaam)_P'FME_NUM_CONDITIONS2___
    -> verzamelaar
AttributeManager_33
    ATTR_TABLE = SET_TO bestandsnaam = FME_CONDITIONAL:DEFAULT_VALUE'_FME_NO_OP_'BOOL_OP;OR;COMPOSITE_TEST;<Unused>;TEST @Value(bestandsnaam) = BGTPLUS_WDI_onbekend'@Value(bestandsnaam)_L'FME_NUM_CONDITIONS2___
    -> verzamelaar_2
imgeo_extractie.vw_imgeo_vegetatieobject (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_18
AttributeManager_18
    ATTR_TABLE:
      RENAME_SET_VALUE einddtijd > eindtijd
      SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
      REMOVE bestandsnaam_plus
    -> GeometryFilter_7
GeometryFilter_7
    INSTANTIATE = Yes
    GEOM_PORT_NAMES = Point Line Area Surface
    BREAK_AGG = Yes
    POINT -> AttributeManager_29
    LINE -> AttributeManager_30
    AREA -> AttributeManager_31
    SURFACE -> AttributeManager_31
AttributeManager_29
    ATTR_TABLE = SET_TO bestandsnaam = FME_CONDITIONAL:DEFAULT_VALUE'_FME_NO_OP_'BOOL_OP;OR;COMPOSITE_TEST;<Unused>;TEST @Value(bestandsnaam) IN BGTPLUS_VGT_haag,BGTPLUS_VGT_onbekend'@Value(bestandsnaam)_P'FME_NUM_CONDITIONS2___
    -> verzamelaar
AttributeManager_30
    ATTR_TABLE = SET_TO bestandsnaam = FME_CONDITIONAL:DEFAULT_VALUE'_FME_NO_OP_'BOOL_OP;OR;COMPOSITE_TEST;<Unused>;TEST @Value(bestandsnaam) IN BGTPLUS_VGT_haag,BGTPLUS_VGT_onbekend'@Value(bestandsnaam)_L'FME_NUM_CONDITIONS2___
    -> verzamelaar_2
AttributeManager_31
    ATTR_TABLE = SET_TO bestandsnaam = FME_CONDITIONAL:DEFAULT_VALUE'_FME_NO_OP_'BOOL_OP;OR;COMPOSITE_TEST;<Unused>;TEST @Value(bestandsnaam) IN BGTPLUS_VGT_haag,BGTPLUS_VGT_onbekend'@Value(bestandsnaam)_V'FME_NUM_CONDITIONS2___
    -> verzamelaar_4
Note: vlakken
verzamelaar_4: Counter
    DOMAIN = counter
    START = 0
    CNT_ATTR = _count
    SCOPE = Global
    -> Shapefile10000 (writer ESRISHAPE_2)
    -> GeometryExtractor_37
    -> SpatialRelator_2 [input 1]
imgeo_extractie.vw_imgeo_sensor (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_17
AttributeManager_17
    ATTR_TABLE:
      RENAME_SET_VALUE einddtijd > eindtijd
      SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
      REMOVE bestandsnaam_plus
    -> GeometryFilter_4
GeometryFilter_4
    INSTANTIATE = Yes
    GEOM_PORT_NAMES = Point Line
    BREAK_AGG = Yes
    POINT -> AttributeManager_27
    LINE -> AttributeManager_28
AttributeManager_27
    ATTR_TABLE = SET_TO bestandsnaam = FME_CONDITIONAL:DEFAULT_VALUE'_FME_NO_OP_'BOOL_OP;OR;COMPOSITE_TEST;<Unused>;TEST @Value(bestandsnaam) = BGTPLUS_SSR_onbekend'@Value(bestandsnaam)_P'FME_NUM_CONDITIONS2___
    -> verzamelaar
AttributeManager_28
    ATTR_TABLE = SET_TO bestandsnaam = FME_CONDITIONAL:DEFAULT_VALUE'_FME_NO_OP_'BOOL_OP;OR;COMPOSITE_TEST;<Unused>;TEST @Value(bestandsnaam) = BGTPLUS_SSR_onbekend'@Value(bestandsnaam)_L'FME_NUM_CONDITIONS2___
    -> verzamelaar_2
imgeo_extractie.vw_imgeo_scheiding (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_2
AttributeManager_2
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_5
GeometryFilter_5
    INSTANTIATE = Yes
    GEOM_PORT_NAMES = Line Area Surface
    BREAK_AGG = Yes
    LINE -> AttributeManager_3
    SURFACE -> AttributeManager_24
    AREA -> AttributeManager_24
AttributeManager_3
    ATTR_TABLE = SET_TO bestandsnaam = FME_CONDITIONAL:DEFAULT_VALUE'_FME_NO_OP_'BOOL_OP;OR;COMPOSITE_TEST;<Unused>;TEST @Value(bestandsnaam) IN BGT_SDG_muur,BGT_SDG_kademuur,BGT_SDG_transitie,BGTPLUS_SDG_onbekend'@Value(bestandsnaam)_L'FME_NUM_CONDITIONS2___
    -> verzamelaar_2
AttributeManager_24
    ATTR_TABLE = SET_TO bestandsnaam = FME_CONDITIONAL:DEFAULT_VALUE'_FME_NO_OP_'BOOL_OP;OR;COMPOSITE_TEST;<Unused>;TEST @Value(bestandsnaam) IN BGT_SDG_muur,BGT_SDG_kademuur,BGT_SDG_transitie,BGTPLUS_SDG_onbekend'@Value(bestandsnaam)_V'FME_NUM_CONDITIONS2___
    -> verzamelaar_3
imgeo_extractie.vw_imgeo_overigescheiding (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_16
AttributeManager_16
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> GeometryFilter_6
GeometryFilter_6
    INSTANTIATE = Yes
    GEOM_PORT_NAMES = Line Area Surface
    BREAK_AGG = Yes
    LINE -> AttributeManager_25
    AREA -> AttributeManager_26
    SURFACE -> AttributeManager_26
AttributeManager_25
    ATTR_TABLE = SET_TO bestandsnaam = FME_CONDITIONAL:DEFAULT_VALUE'_FME_NO_OP_'BOOL_OP;OR;COMPOSITE_TEST;<Unused>;TEST @Value(bestandsnaam) IN BGTPLUS_OSDG_muur,BGTPLUS_OSDG_kademuur,BGTPLUS_OSDG_onbekend'@Value(bestandsnaam)_L'FME_NUM_CONDITIONS2___
    -> verzamelaar_2
AttributeManager_26
    ATTR_TABLE = SET_TO bestandsnaam = FME_CONDITIONAL:DEFAULT_VALUE'_FME_NO_OP_'BOOL_OP;OR;COMPOSITE_TEST;<Unused>;TEST @Value(bestandsnaam) IN BGTPLUS_OSDG_muur,BGTPLUS_OSDG_kademuur,BGTPLUS_OSDG_onbekend'@Value(bestandsnaam)_V'FME_NUM_CONDITIONS2___
    -> verzamelaar_3
imgeo_extractie.vw_imgeo_kunstwerkdeel (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_15
AttributeManager_15
    ATTR_TABLE:
      RENAME_SET_VALUE einddtijd > eindtijd
      SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
      REMOVE bestandsnaam_plus
    -> GeometryFilter_9
GeometryFilter_9
    INSTANTIATE = Yes
    GEOM_PORT_NAMES = Point Line Area Surface
    BREAK_AGG = Yes
    LINE -> AttributeManager_21
    POINT -> AttributeManager_22
    AREA -> AttributeManager_23
    SURFACE -> AttributeManager_23
AttributeManager_22
    ATTR_TABLE = SET_TO bestandsnaam = FME_CONDITIONAL:DEFAULT_VALUE'_FME_NO_OP_'BOOL_OP;OR;COMPOSITE_TEST;<Unused>;TEST @Value(bestandsnaam) IN BGT_KDL_hoogspanningsmast,BGT_KDL_transitie, BGT_KDL_onbekend'@Value(bestandsnaam)_P'FME_NUM_CONDITIONS2___
    -> verzamelaar
Note: verzamelaar puntenobjecten
verzamelaar: Counter
    DOMAIN = counter
    START = 0
    CNT_ATTR = _count
    SCOPE = Global
    -> GeometryExtractor_35
    -> Shapefile1 (writer ESRISHAPE_2)
    -> SpatialRelator_2 [input 1]
AttributeManager_21
    ATTR_TABLE = SET_TO bestandsnaam = FME_CONDITIONAL:DEFAULT_VALUE'_FME_NO_OP_'BOOL_OP;OR;COMPOSITE_TEST;<Unused>;TEST @Value(bestandsnaam) IN BGT_KDL_stuw,BGT_KDL_transitie,BGTPLUS_KDL_duiker,BGTPLUS_KDL_onbekend'@Value(bestandsnaam)_L'FME_NUM_CONDITIONS2___
    -> verzamelaar_2
Note: verzamelaar lijnobjecten
verzamelaar_2: Counter
    DOMAIN = counter
    START = 0
    CNT_ATTR = _count
    SCOPE = Global
    -> GeometryExtractor_36
    -> Shapefile100 (writer ESRISHAPE_2)
    -> SpatialRelator_2 [input 1]
AttributeManager_23
    ATTR_TABLE = SET_TO bestandsnaam = FME_CONDITIONAL:DEFAULT_VALUE'_FME_NO_OP_'BOOL_OP;OR;COMPOSITE_TEST;<Unused>;TEST @Value(bestandsnaam) IN BGT_KDL_hoogspanningsmast,BGT_KDL_transitie,BGT_KDL_stuw,BGTPLUS_KDL_duiker,BGTPLUS_KDL_onbekend'@Value(bestandsnaam)_V'FME_NUM_CONDITIONS2___
    -> verzamelaar_3
imgeo_extractie.vw_imgeo_overigbouwwerk (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_10
AttributeManager_10
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar_3
imgeo_extractie.vw_imgeo_gebouwinstallatie (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text
    -> AttributeManager_7
AttributeManager_7
    ATTR_TABLE = SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
    -> verzamelaar_3
Note: imgeo objecten: geometrietype vlakken
verzamelaar_3: Counter
    DOMAIN = counter
    START = 0
    CNT_ATTR = _count
    SCOPE = Global
    -> GeometryExtractor_37
    -> Shapefile10000 (writer ESRISHAPE_2)
    -> SpatialRelator_2 [input 1]

Bookmark: Esri_Shape totaal voor punt-, lijn- en vlakobjecten
Note: Punten_shps
Shapefile1 (writer ESRISHAPE_2)
    attributes: namespace char(8), lokaalid char(38), begintijd date, eindtijd char(200), tijdreg char(20), eindreg char(20), lv_pubdat char(20), bronhoud char(40), inonderzk char(1), hoogtelig short, bgtstatus char(8), plusstatus char(8), bgttype char(200), plustype char(200)
Note: Lijnen
Shapefile100 (writer ESRISHAPE_2)
    attributes: namespace char(8), lokaalid char(38), begintijd date, eindtijd date, tijdreg char(20), eindreg char(20), lv_pubdat char(20), bronhoud char(40), inonderzk char(1), hoogtelig short, bgtstatus char(8), plusstatus char(8), bgttype char(200), plustype char(200)
Note: Vlakken
Shapefile10000 (writer ESRISHAPE_2)
    attributes: namespace char(8), lokaalid char(38), begintijd date, eindtijd date, tijdreg char(20), eindreg char(20), lv_pubdat char(20), bronhoud char(40), inonderzk char(1), hoogtelig short, bgtstatus char(8), plusstatus char(8), bgttype char(200), plustype char(200)

Bookmark: CSV Totaal voor punt-, lijn- en vlakobjecten
Note: GeometryExtractor_punten2csv
GeometryExtractor_35
    ATTR = geometrie
    KIND_LONG = OGC Well Known Text
    OGCVERSION = 1.1
    OGC_WKT_PRECISION_DISPLAY = Shortened 64-bit
    REMOVE_GEOMETRY = No
    -> AttributeManager_39
AttributeManager_39
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
      REMOVE einddtijd
      REMOVE bestandsnaam_plus
      REMOVE _count
    -> imgeo_extractie.vw_bgt_waterdeel01 (writer CSV_2)
Note: punten: csv_totaal [CSV]
imgeo_extractie.vw_bgt_waterdeel01 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-type auto, plus-type auto, geometrie float
GeometryExtractor_36
    ATTR = geometrie
    KIND_LONG = OGC Well Known Text
    OGCVERSION = 1.1
    OGC_WKT_PRECISION_DISPLAY = Shortened 64-bit
    REMOVE_GEOMETRY = No
    -> AttributeManager_40
AttributeManager_40
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
      REMOVE einddtijd
      REMOVE bestandsnaam_plus
      REMOVE _count
    -> imgeo_extractie.vw_bgt_waterdeel02 (writer CSV_2)
Note: : ASCII_totaal [CSV]
imgeo_extractie.vw_bgt_waterdeel02 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-type auto, plus-type auto, geometrie float
GeometryExtractor_37
    ATTR = geometrie
    KIND_LONG = OGC Well Known Text
    OGCVERSION = 1.1
    OGC_WKT_PRECISION_DISPLAY = Shortened 64-bit
    REMOVE_GEOMETRY = No
    -> AttributeManager_41
AttributeManager_41
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
      REMOVE einddtijd
      REMOVE bestandsnaam_plus
      REMOVE _count
    -> imgeo_extractie.vw_bgt_waterdeel03 (writer CSV_2)
Note: : ASCII_totaal [CSV]
imgeo_extractie.vw_bgt_waterdeel03 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-type auto, plus-type auto, geometrie float

Bookmark: Paal en functioneelgebied moet apart worden behandeld omdat de attributen specifiek zijn
imgeo_extractie.vw_imgeo_paal (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text, hm_aand varchar(200)
    -> AttributeManager_11
AttributeManager_11
    ATTR_TABLE:
      RENAME_SET_VALUE einddtijd > eindtijd
      SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'FME_NUM_CONDITIONS2___
      REMOVE bestandsnaam_plus
    -> GeometryExtractor_18
    -> Shapefile1000000 (writer ESRISHAPE_2)
    -> SpatialRelator_2 [input 1]
GeometryExtractor_18
    ATTR = geometrie
    KIND_LONG = OGC Well Known Text
    OGCVERSION = 1.1
    OGC_WKT_PRECISION_DISPLAY = Shortened 64-bit
    REMOVE_GEOMETRY = No
    -> AttributeManager_45
AttributeManager_45
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
      RENAME_SET_VALUE hm_aand > hectometeraanduiding
    -> imgeo_extractie.vw_bgt_waterdeel (writer CSV_2)
Note: : ASCII_totaal [CSV]
imgeo_extractie.vw_bgt_waterdeel (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-type auto, plus-type auto, hectometeraanduiding auto, geometrie float
Note: Paal: shp_totaal [ESRISHAPE]
Shapefile1000000 (writer ESRISHAPE_2)
    attributes: namespace char(8), lokaalid char(38), begintijd date, eindtijd date, tijdreg char(20), eindreg char(20), lv_pubdat char(20), bronhoud char(40), inonderzk char(1), hoogtelig short, bgtstatus char(8), plusstatus char(8), bgttype char(200), plustype char(200), hm_aand char(200)
imgeo_extractie.vw_imgeo_functioneelgebied (reader POSTGIS_2)
    attributes: namespace varchar(8), lokaalid varchar(38), begintijd date, einddtijd date, tijdreg timestamp, eindreg timestamp, lv_pubdat timestamp, bronhoud varchar(40), inonderzk varchar(1), hoogtelig int2, bgtstatus varchar(8), plusstatus varchar(8), bgttype varchar(200), bestandsnaam text, plustype varchar(200), bestandsnaam_plus text, naam varchar(200)
    -> AttributeManager_6
Note: bestandsnaam = BGTPLUS_FGD_halte als plus_type = halte
AttributeManager_6
    ATTR_TABLE:
      RENAME_SET_VALUE einddtijd > eindtijd
      SET_TO bestandsnaam = FME_CONDITIONAL:DEFAULT_VALUE'_FME_NO_OP_'BOOL_OP;OR;COMPOSITE_TEST;<Unused>;TEST bestandsnaam ATTRIBUTE_VALUE_NULL _FME_BLANK_STRING_'@Value(bestandsnaam_plus)'BOOL_OP;OR;COMPOSITE_TEST;<Unused>;TEST @Value(plustype) = halte'BGTPLUS_FGD_halte'FME_NUM_CONDITIONS3___
      REMOVE bestandsnaam_plus
    -> GeometryExtractor_19
    -> Shapefile100000002 (writer ESRISHAPE_2)
    -> SpatialRelator_2 [input 1]
Note: Funct.gebied: shp_totaal [ESRISHAPE]
Shapefile100000002 (writer ESRISHAPE_2)
    attributes: namespace char(8), lokaalid char(38), begintijd date, eindtijd date, tijdreg char(20), eindreg char(20), lv_pubdat char(20), bronhoud char(40), inonderzk char(1), hoogtelig short, bgtstatus char(8), plusstatus char(8), bgttype char(200), plustype char(200), naam char(200)
GeometryExtractor_19
    ATTR = geometrie
    KIND_LONG = OGC Well Known Text
    OGCVERSION = 1.1
    OGC_WKT_PRECISION_DISPLAY = Shortened 64-bit
    REMOVE_GEOMETRY = No
    -> AttributeManager_48
AttributeManager_48
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
    -> imgeo_extractie.vw_bgt_waterdeel00 (writer CSV_2)
Note: funct.gebied: csv_totaal [CSV]
imgeo_extractie.vw_bgt_waterdeel00 (writer CSV_2)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-type auto, plus-type auto, naam text, geometrie float

Bookmark: Bepalen objecteklassen per kaartblad
imgeo.pdt_kaartblad (reader POSTGIS_1)
    attributes: id serial,PRIKEY, naam varchar(200), big_id int4
    -> SpatialRelator_2 [input 2]
ListExploder_2
    INDEX_ATTR = _element_index
    ATTR_ACCUM_MODE = Prefix Incoming List
    LIST_ATTR = _relationships{}
    INCOMING_PREFIX = test
    ELEMENTS -> AttributeManager_113
AttributeManager_113
    ATTR_TABLE:
      RENAME_SET_VALUE testnaam > gebied
      REMOVE testde9im
      REMOVE testpass{}
      REMOVE _related_candidates
      REMOVE _element_index
    -> AttributeFilter

Bookmark: Uitsplitsen op geometrietype en objectklassen
Note: AttributeFilter: filteren van views waarbij attributen aangepast dienen te worden tbv Esri_Shape en Ascii bestanden
AttributeFilter
    ATTR_NAME = fme_feature_type
    ATTR_VALUES = <EMPTY>,<MISSING>,<NULL>,<UNFILTERED>,imgeo_extractie.vw_imgeo_paal,imgeo_extractie.vw_imgeo_functioneelgebied,imgeo_extractie.vw_bgt_overbruggingsdeel,imgeo_extractie.vw_bgt_tunneldeel,imgeo_extractie.vw_imgeo_spoor,imgeo_extractie.vw_bgt_ongeclassificeerdobject,imgeo_extractie.vw_bgt_pand,imgeo_extractie.vw_bgt_kruinlijn,imgeo_extractie.vw_bag_standplaats,imgeo_extractie.vw_bag_ligplaats,imgeo_extractie.vw_cft_overbouw,imgeo_extractie.vw_cft_onderbouw,imgeo_extractie.vw_bgt_openbareruimtelabel,imgeo_extractie.vw_bgt_nummeraanduidingreeks,imgeo_extractie.vw_bgt_ondersteunendwegdeel,imgeo_extractie.vw_bgt_wegdeel,imgeo_extractie.vw_bgt_begroeidterreindeel,imgeo_extractie.vw_bgt_onbegroeidterreindeel,imgeo_extractie.vw_bgt_ondersteunendwaterdeel,imgeo_extractie.vw_bgt_waterdeel,imgeo_extractie.vw_lps_nummeraanduiding,imgeo_extractie.vw_sps_nummeraanduiding
    imgeo_extractie.vw_bgt_nummeraanduidingreeks -> GeometryExtractor_8
    imgeo_extractie.vw_bag_ligplaats -> AttributeKeeper_5
    imgeo_extractie.vw_bag_standplaats -> AttributeKeeper_6
    imgeo_extractie.vw_cft_overbouw -> AttributeKeeper_7
    imgeo_extractie.vw_cft_onderbouw -> AttributeKeeper_8
    imgeo_extractie.vw_imgeo_paal -> GeometryExtractor_7
    imgeo_extractie.vw_imgeo_paal -> imgeo_extractie.vw_imgeo_kunstwerkdeel_point01 (writer ESRISHAPE_1)
    imgeo_extractie.vw_imgeo_functioneelgebied -> GeometryExtractor_17
    imgeo_extractie.vw_imgeo_functioneelgebied -> imgeo_extractie.vw_imgeo_kunstwerkdeel_point0100 (writer ESRISHAPE_1)
    imgeo_extractie.vw_bgt_pand -> PartCounter_2
    imgeo_extractie.vw_bgt_pand -> imgeo_extractie.vw_imgeo_kunstwerkdeel_polygon0000 (writer ESRISHAPE_1)
    imgeo_extractie.vw_bgt_tunneldeel -> GeometryExtractor_38
    imgeo_extractie.vw_bgt_tunneldeel -> imgeo_extractie.vw_imgeo_kunstwerkdeel_point010000 (writer ESRISHAPE_1)
    imgeo_extractie.vw_bgt_ongeclassificeerdobject -> GeometryExtractor_40
    imgeo_extractie.vw_bgt_ongeclassificeerdobject -> imgeo_extractie.vw_imgeo_kunstwerkdeel_point010000000000 (writer ESRISHAPE_1)
    imgeo_extractie.vw_bgt_kruinlijn -> GeometryExtractor_4
    imgeo_extractie.vw_bgt_openbareruimtelabel -> GeometryExtractor_41
    imgeo_extractie.vw_bgt_openbareruimtelabel -> imgeo_extractie.vw_imgeo_kunstwerkdeel_point0000 (writer ESRISHAPE_1)
    imgeo_extractie.vw_bgt_nummeraanduidingreeks -> imgeo_extractie.vw_imgeo_kunstwerkdeel_point00 (writer ESRISHAPE_1)
    imgeo_extractie.vw_bgt_ondersteunendwegdeel -> imgeo_extractie.vw_imgeo_kunstwerkdeel_point0001 (writer ESRISHAPE_1)
    imgeo_extractie.vw_bgt_wegdeel -> GeometryExtractor_43
    imgeo_extractie.vw_bgt_wegdeel -> imgeo_extractie.vw_imgeo_kunstwerkdeel_point000100 (writer ESRISHAPE_1)
    imgeo_extractie.vw_bgt_begroeidterreindeel -> GeometryExtractor_44
    imgeo_extractie.vw_bgt_begroeidterreindeel -> imgeo_extractie.vw_imgeo_kunstwerkdeel_point00010000 (writer ESRISHAPE_1)
    imgeo_extractie.vw_bgt_onbegroeidterreindeel -> GeometryExtractor_45
    imgeo_extractie.vw_bgt_onbegroeidterreindeel -> imgeo_extractie.vw_imgeo_kunstwerkdeel_point0001000000 (writer ESRISHAPE_1)
    imgeo_extractie.vw_bgt_ondersteunendwaterdeel -> GeometryExtractor_46
    imgeo_extractie.vw_bgt_ondersteunendwaterdeel -> imgeo_extractie.vw_imgeo_kunstwerkdeel_point000100000000 (writer ESRISHAPE_1)
    imgeo_extractie.vw_bgt_waterdeel -> GeometryExtractor_47
    imgeo_extractie.vw_bgt_waterdeel -> imgeo_extractie.vw_imgeo_kunstwerkdeel_point00010000000000 (writer ESRISHAPE_1)
    imgeo_extractie.vw_bgt_kruinlijn -> AttributeManager_38
    <UNFILTERED> -> GeometryFilter
    imgeo_extractie.vw_bgt_overbruggingsdeel -> AttributeFilter_3
    imgeo_extractie.vw_imgeo_spoor -> imgeo_extractie.vw_imgeo_kunstwerkdeel_point01000000 (writer ESRISHAPE_1)
    imgeo_extractie.vw_imgeo_spoor -> GeometryExtractor_3
    imgeo_extractie.vw_bgt_ondersteunendwegdeel -> GeometryExtractor_42
    imgeo_extractie.vw_sps_nummeraanduiding -> bestandsnaam000000 (writer ESRISHAPE_1)
    imgeo_extractie.vw_sps_nummeraanduiding -> GeometryExtractor_61
    imgeo_extractie.vw_lps_nummeraanduiding -> GeometryExtractor_62
    imgeo_extractie.vw_lps_nummeraanduiding -> bestandsnaam00000000 (writer ESRISHAPE_1)
GeometryFilter
    GEOM_PORT_NAMES = Point Line Area
    BREAK_AGG = No
    POINT -> GeometryExtractor_12
    LINE -> GeometryExtractor_13
    AREA -> GeometryExtractor_2
    AREA -> imgeo_extractie.vw_imgeo_kunstwerkdeel_polygon01 (writer ESRISHAPE_1)
    LINE -> imgeo_extractie.vw_imgeo_kunstwerkdeel_line00 (writer ESRISHAPE_1)
    POINT -> imgeo_extractie.vw_imgeo_kunstwerkdeel_point02 (writer ESRISHAPE_1)

Bookmark: ASCII per gebied
GeometryExtractor_7
    ATTR = geometrie
    KIND_LONG = OGC Well Known Text
    OGCVERSION = 1.1
    OGC_WKT_PRECISION_DISPLAY = Shortened 64-bit
    REMOVE_GEOMETRY = No
    -> AttributeManager_46
AttributeManager_46
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
      RENAME_SET_VALUE hm_aand > hectometeraanduiding
      REMOVE bestandsnaam_plus
      REMOVE _count
    -> imgeo_extractie.vw_imgeo_scheiding02 (writer CSV_1)
Note: Paal: csv_gebied [CSV]
imgeo_extractie.vw_imgeo_scheiding02 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-type auto, plus-type auto, hectometeraanduiding auto, geometrie float
GeometryExtractor_17
    ATTR = geometrie
    KIND_LONG = OGC Well Known Text
    OGCVERSION = 1.1
    OGC_WKT_PRECISION_DISPLAY = Shortened 64-bit
    REMOVE_GEOMETRY = No
    -> AttributeManager_47
AttributeManager_47
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
      REMOVE fme_feature_type
      REMOVE bestandsnaam_plus
      REMOVE _count
      REMOVE hm_aand
    -> imgeo_extractie.vw_imgeo_scheiding0200 (writer CSV_1)
Note: Funct.gebied: csv_gebied [CSV]
imgeo_extractie.vw_imgeo_scheiding0200 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-type auto, plus-type auto, naam auto, geometrie float
GeometryExtractor_12
    ATTR = geometrie
    KIND_LONG = OGC Well Known Text
    OGCVERSION = 1.1
    OGC_WKT_PRECISION_DISPLAY = Shortened 64-bit
    REMOVE_GEOMETRY = No
    -> AttributeManager_42
AttributeManager_42
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
      REMOVE einddtijd
      REMOVE bestandsnaam_plus
      REMOVE _count
      REMOVE fme_feature_type
      REMOVE hm_aand
    -> imgeo_extractie.vw_imgeo_scheiding03 (writer CSV_1)
Note: punten: ASCII_gebied [CSV
imgeo_extractie.vw_imgeo_scheiding03 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-type auto, plus-type auto, geometrie float
GeometryExtractor_13
    ATTR = geometrie
    KIND_LONG = OGC Well Known Text
    OGCVERSION = 1.1
    OGC_WKT_PRECISION_DISPLAY = Shortened 64-bit
    REMOVE_GEOMETRY = No
    -> AttributeManager_43
AttributeManager_43
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
      REMOVE einddtijd
      REMOVE bestandsnaam_plus
      REMOVE _count
      REMOVE fme_feature_type
      REMOVE hm_aand
    -> imgeo_extractie.vw_imgeo_scheiding0000 (writer CSV_1)
Note: lijnen: ASCII_gebied [CSV]
imgeo_extractie.vw_imgeo_scheiding0000 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-type auto, plus-type auto, geometrie float
GeometryExtractor_2
    ATTR = geometrie
    KIND_LONG = OGC Well Known Text
    OGCVERSION = 1.1
    OGC_WKT_PRECISION_DISPLAY = Shortened 64-bit
    REMOVE_GEOMETRY = No
    -> AttributeManager_44
AttributeManager_44
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgttype > bgt-type
      RENAME_SET_VALUE plustype > plus-type
      REMOVE _count
      REMOVE fme_feature_type
      REMOVE bestandsnaam_plus
      REMOVE hm_aand
    -> imgeo_extractie.vw_imgeo_scheiding000101 (writer CSV_1)
Note: vlakken: ASCII_gebied [CSV]
imgeo_extractie.vw_imgeo_scheiding000101 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-type auto, plus-type auto, geometrie float
GeometryExtractor_57
    ATTR = geometrie
    KIND_LONG = OGC Well Known Text
    OGCVERSION = 1.1
    OGC_WKT_PRECISION_DISPLAY = Shortened 64-bit
    REMOVE_GEOMETRY = No
    -> AttributeManager_94
AttributeManager_94
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
      RENAME_SET_VALUE isbeweegb > overbruggingisbeweegbaar
      REMOVE fme_feature_type
      REMOVE bestandsnaam_plus
      REMOVE _count
      REMOVE hm_aand
    -> imgeo_extractie.vw_imgeo_scheiding02000000000100000000 (writer CSV_1)
Note: overbrug.deel: csv_gebied [CSV]
imgeo_extractie.vw_imgeo_scheiding02000000000100000000 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, type auto, hoortbijtypeoverbrugging auto, overbruggingisbeweegbaar auto, geometrie float
GeometryExtractor_39
    ATTR = geometrie
    KIND_LONG = OGC Well Known Text
    OGCVERSION = 1.1
    OGC_WKT_PRECISION_DISPLAY = Shortened 64-bit
    REMOVE_GEOMETRY = No
    -> AttributeManager_54
AttributeManager_54
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
      RENAME_SET_VALUE isbeweegb > overbruggingisbeweegbaar
      REMOVE fme_feature_type
      REMOVE bestandsnaam_plus
      REMOVE _count
      REMOVE hm_aand
    -> imgeo_extractie.vw_imgeo_scheiding0200000000 (writer CSV_1)
Note: overbrug.deel_pijler: csv_gebied [CSV]
imgeo_extractie.vw_imgeo_scheiding0200000000 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, type auto, hoortbijtypeoverbrugging auto, overbruggingisbeweegbaar auto, geometrie float
GeometryExtractor_49
    ATTR = geometrie
    KIND_LONG = OGC Well Known Text
    OGCVERSION = 1.1
    OGC_WKT_PRECISION_DISPLAY = Shortened 64-bit
    REMOVE_GEOMETRY = No
    -> AttributeManager_86
AttributeManager_86
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
      RENAME_SET_VALUE isbeweegb > overbruggingisbeweegbaar
    -> imgeo_extractie.vw_imgeo_scheiding020000000001 (writer CSV_1)
Note: overbrug.deel: csv_gebied [CSV]
imgeo_extractie.vw_imgeo_scheiding020000000001 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, type auto, hoortbijtypeoverbrugging auto, overbruggingisbeweegbaar auto, geometrie float
GeometryExtractor_53
    ATTR = geometrie
    KIND_LONG = OGC Well Known Text
    OGCVERSION = 1.1
    OGC_WKT_PRECISION_DISPLAY = Shortened 64-bit
    REMOVE_GEOMETRY = No
    -> AttributeManager_90
AttributeManager_90
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
      RENAME_SET_VALUE isbeweegb > overbruggingisbeweegbaar
      REMOVE fme_feature_type
      REMOVE bestandsnaam_plus
      REMOVE _count
      REMOVE hm_aand
    -> imgeo_extractie.vw_imgeo_scheiding0200000000010000 (writer CSV_1)
Note: overbrug.deel: csv_gebied [CSV]
imgeo_extractie.vw_imgeo_scheiding0200000000010000 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, type auto, hoortbijtypeoverbrugging auto, overbruggingisbeweegbaar auto, geometrie float
GeometryExtractor_55
    ATTR = geometrie
    KIND_LONG = OGC Well Known Text
    OGCVERSION = 1.1
    OGC_WKT_PRECISION_DISPLAY = Shortened 64-bit
    REMOVE_GEOMETRY = No
    -> AttributeManager_92
AttributeManager_92
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
      RENAME_SET_VALUE isbeweegb > overbruggingisbeweegbaar
      REMOVE fme_feature_type
      REMOVE bestandsnaam_plus
      REMOVE _count
      REMOVE hm_aand
    -> imgeo_extractie.vw_imgeo_scheiding020000000001000000 (writer CSV_1)
Note: overbrug.deel: csv_gebied [CSV]
imgeo_extractie.vw_imgeo_scheiding020000000001000000 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, type auto, hoortbijtypeoverbrugging auto, overbruggingisbeweegbaar auto, geometrie float
AttributeManager_88
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE hoortbij > hoortbijtypeoverbrugging
      RENAME_SET_VALUE isbeweegb > overbruggingisbeweegbaar
    -> imgeo_extractie.vw_imgeo_scheiding02000000000100 (writer CSV_1)
Note: overbrug.deel: csv_gebied [CSV]
imgeo_extractie.vw_imgeo_scheiding02000000000100 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, type auto, hoortbijtypeoverbrugging auto, overbruggingisbeweegbaar auto, geometrie float
GeometryExtractor_38
    ATTR = geometrie
    KIND_LONG = OGC Well Known Text
    OGCVERSION = 1.1
    OGC_WKT_PRECISION_DISPLAY = Shortened 64-bit
    REMOVE_GEOMETRY = No
    -> AttributeManager_50
AttributeManager_50
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      REMOVE fme_feature_type
      REMOVE bestandsnaam_plus
      REMOVE _count
      REMOVE hm_aand
    -> imgeo_extractie.vw_imgeo_scheiding020000 (writer CSV_1)
Note: Tuneeldee;l: csv_gebied [CSV]
imgeo_extractie.vw_imgeo_scheiding020000 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, geometrie float
GeometryExtractor_3
    ATTR = geometrie
    KIND_LONG = OGC Well Known Text
    OGCVERSION = 1.1
    OGC_WKT_PRECISION_DISPLAY = Shortened 64-bit
    REMOVE_GEOMETRY = No
    -> AttributeManager_52
AttributeManager_52
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfunctie > bgt-functie
      RENAME_SET_VALUE plusfunct > plus-functie
      REMOVE fme_feature_type
      REMOVE bestandsnaam_plus
      REMOVE _count
      REMOVE hm_aand
    -> imgeo_extractie.vw_imgeo_scheiding02000000 (writer CSV_1)
Note: Spoorl: csv_gebied [CSV]
imgeo_extractie.vw_imgeo_scheiding02000000 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-functie auto, plus-functie auto, geometrie float
GeometryExtractor_40
    ATTR = geometrie
    KIND_LONG = OGC Well Known Text
    OGCVERSION = 1.1
    OGC_WKT_PRECISION_DISPLAY = Shortened 64-bit
    REMOVE_GEOMETRY = No
    -> AttributeManager_56
AttributeManager_56
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
    -> imgeo_extractie.vw_imgeo_scheiding020000000000 (writer CSV_1)
Note: oongeclass.: csv_gebied [CSV]
imgeo_extractie.vw_imgeo_scheiding020000000000 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, geometrie float
GeometryExtractor_26
    ATTR = geometrie
    KIND_LONG = OGC Well Known Text
    OGCVERSION = 1.1
    OGC_WKT_PRECISION_DISPLAY = Shortened 64-bit
    REMOVE_GEOMETRY = No
    -> AttributeManager_58
AttributeManager_58
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bagpndid > identificatieBAGPND
      REMOVE _part_count
      REMOVE _hierarchy_child_id_list{}
      REMOVE _geometry_name
      REMOVE _hierarchy_id
      REMOVE _hierarchy_parent_id
      REMOVE _part_number
    -> imgeo_extractie.vw_imgeo_scheiding00010000 (writer CSV_1)
Note: Pand: csv_gebied [CSV]
imgeo_extractie.vw_imgeo_scheiding00010000 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, identificatieBAGPND auto, geometrie float
GeometryExtractor_4
    ATTR = geometrie
    KIND_LONG = OGC Well Known Text
    OGCVERSION = 1.1
    OGC_WKT_PRECISION_DISPLAY = Shortened 64-bit
    REMOVE_GEOMETRY = No
    -> AttributeManager_60
AttributeManager_60
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
    -> imgeo_extractie.vw_imgeo_scheiding000100 (writer CSV_1)
Note: Kruinlijn: csv_gebied [CSV]
imgeo_extractie.vw_imgeo_scheiding000100 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, optalud text, hoortbij text, geometrie float
GeometryExtractor_14
    ATTR = geometrie
    KIND_LONG = OGC Well Known Text
    OGCVERSION = 1.1
    OGC_WKT_PRECISION_DISPLAY = Shortened 64-bit
    REMOVE_GEOMETRY = No
    -> AttributeManager_62
AttributeManager_62
    ATTR_TABLE = RENAME_SET_VALUE bagid > BAG_identificatie
    -> imgeo_extractie.vw_imgeo_scheiding0001000000 (writer CSV_1)
Note: BAG_Standplaats: csv_gebied [CSV]
imgeo_extractie.vw_imgeo_scheiding0001000000 (writer CSV_1)
    attributes: BAG_identificatie auto, geometrie auto
GeometryExtractor_9
    ATTR = geometrie
    KIND_LONG = OGC Well Known Text
    OGCVERSION = 1.1
    OGC_WKT_PRECISION_DISPLAY = Shortened 64-bit
    REMOVE_GEOMETRY = No
    -> AttributeManager_64
AttributeManager_64
    ATTR_TABLE = RENAME_SET_VALUE bagid > BAG_identificatie
    -> imgeo_extractie.vw_imgeo_scheiding00010001 (writer CSV_1)
Note: BAG_Ligplaats: csv_gebied [CSV]
imgeo_extractie.vw_imgeo_scheiding00010001 (writer CSV_1)
    attributes: BAG_identificatie auto, geometrie auto
GeometryExtractor_15
    ATTR = geometrie
    KIND_LONG = OGC Well Known Text
    OGCVERSION = 1.1
    OGC_WKT_PRECISION_DISPLAY = Shortened 64-bit
    REMOVE_GEOMETRY = No
    -> AttributeManager_66
AttributeManager_66
    ATTR_TABLE:
      RENAME_SET_VALUE eindreg > eindregistratie
      RENAME_SET_VALUE hoogtelig > relatievehoogteligging
    -> imgeo_extractie.vw_imgeo_scheiding000100000101 (writer CSV_1)
Note: Overbouw: ASCII_gebied [CSV]
imgeo_extractie.vw_imgeo_scheiding000100000101 (writer CSV_1)
    attributes: guid auto, eindregistratie char(20), relatievehoogteligging auto, geometrie auto
GeometryExtractor_16
    ATTR = geometrie
    KIND_LONG = OGC Well Known Text
    OGCVERSION = 1.1
    OGC_WKT_PRECISION_DISPLAY = Shortened 64-bit
    REMOVE_GEOMETRY = No
    -> AttributeManager_68
AttributeManager_68
    ATTR_TABLE:
      RENAME_SET_VALUE eindreg > eindregistratie
      RENAME_SET_VALUE hoogtelig > relatievehoogteligging
    -> imgeo_extractie.vw_imgeo_scheiding00010000010000 (writer CSV_1)
Note: Onderbouw: ASCII_gebied [CSV]
imgeo_extractie.vw_imgeo_scheiding00010000010000 (writer CSV_1)
    attributes: guid auto, eindregistratie char(20), relatievehoogteligging auto, geometrie auto
GeometryExtractor_41
    ATTR = geometrie
    KIND_LONG = OGC Well Known Text
    OGCVERSION = 1.1
    OGC_WKT_PRECISION_DISPLAY = Shortened 64-bit
    REMOVE_GEOMETRY = No
    -> AttributeManager_70
AttributeManager_70
    ATTR_TABLE:
      RENAME_SET_VALUE namespace > identificatie_namespace
      RENAME_SET_VALUE lokaalid > identificatie_lokaalid
      RENAME_SET_VALUE begintijd > objectbegintijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE einddtijd > objecteindtijd
      RENAME_SET_VALUE bagoprid > identificatieBAGOPR
      RENAME_SET_VALUE oprtype > openbareruimtetype
    -> imgeo_extractie.vw_imgeo_scheiding0100 (writer CSV_1)
Note: Openbareruimte: csv_gebied [CSV]
imgeo_extractie.vw_imgeo_scheiding0100 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, identificatieBAGOPR auto, openbareruimtetype auto, tekst float, hoek float, geometrie float
GeometryExtractor_8
    ATTR = geometrie
    KIND_LONG = OGC Well Known Text
    OGCVERSION = 1.1
    OGC_WKT_PRECISION_DISPLAY = Shortened 64-bit
    REMOVE_GEOMETRY = No
    -> AttributeManager_72
AttributeManager_72
    ATTR_TABLE:
      RENAME_SET_VALUE tekst_afk > tekst_afgekort
      RENAME_SET_VALUE bagpndid > identificatieBAGPND
      RENAME_SET_VALUE bagvbolgst > identificatieBAGVBOLaagsteHuisnummer
      RENAME_SET_VALUE bagvbohgst > identificatieBAGVBOHoogsteHuisnummer
      RENAME_SET_VALUE lokaalid > identificatie_lokaalid
    -> imgeo_extractie.vw_imgeo_scheiding01 (writer CSV_1)
Note: Huisnrs: csv_gebied [CSV]
imgeo_extractie.vw_imgeo_scheiding01 (writer CSV_1)
    attributes: identificatie_lokaalid auto, identificatieBAGPND auto, tekst float, tekst_afgekort auto, identificatieBAGVBOLaagsteHuisnummer auto, identificatieBAGVBOHoogsteHuisnummer auto, hoek float, geometrie float
GeometryExtractor_42
    ATTR = geometrie
    KIND_LONG = OGC Well Known Text
    OGCVERSION = 1.1
    OGC_WKT_PRECISION_DISPLAY = Shortened 64-bit
    REMOVE_GEOMETRY = No
    -> AttributeManager_74
AttributeManager_74
    ATTR_TABLE:
      RENAME_SET_VALUE namespace > identificatie_namespace
      RENAME_SET_VALUE lokaalid > identificatie_lokaalid
      RENAME_SET_VALUE begintijd > objectbegintijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE einddtijd > objecteindtijd
      RENAME_SET_VALUE bgtfunctie > bgt-functie
      RENAME_SET_VALUE bgtfysvkn > bgt-fysiekvoorkomen
      RENAME_SET_VALUE plusfunct > plus-functie
      RENAME_SET_VALUE plusfysvkn > plus-fysiekvoorkomen
      REMOVE fme_feature_type
      REMOVE bestandsnaam_plus
      REMOVE _count
      REMOVE hm_aand
    -> imgeo_extractie.vw_imgeo_scheiding0101 (writer CSV_1)
Note: Wegdeel: csv_gebied [CSV]
imgeo_extractie.vw_imgeo_scheiding0101 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, optalud text, bgt-functie auto, bgt-fysiekvoorkomen auto, plus-functie auto, plus-fysiekvoorkomen auto, geometrie float
GeometryExtractor_43
    ATTR = geometrie
    KIND_LONG = OGC Well Known Text
    OGCVERSION = 1.1
    OGC_WKT_PRECISION_DISPLAY = Shortened 64-bit
    REMOVE_GEOMETRY = No
    -> AttributeManager_75
AttributeManager_75
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfunctie > bgt-functie
      RENAME_SET_VALUE bgtfysvkn > bgt-fysiekvoorkomen
      RENAME_SET_VALUE plusfunct > plus-functie
      RENAME_SET_VALUE plusfysvkn > plus-fysiekvoorkomen
      REMOVE fme_feature_type
      REMOVE bestandsnaam_plus
      REMOVE _count
      REMOVE hm_aand
    -> imgeo_extractie.vw_imgeo_scheiding010100 (writer CSV_1)
Note: Wegdeel: csv_gebied [CSV]
imgeo_extractie.vw_imgeo_scheiding010100 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-functie auto, bgt-fysiekvoorkomen auto, optalud text, plus-functie auto, plus-fysiekvoorkomen auto, geometrie float
GeometryExtractor_44
    ATTR = geometrie
    KIND_LONG = OGC Well Known Text
    OGCVERSION = 1.1
    OGC_WKT_PRECISION_DISPLAY = Shortened 64-bit
    REMOVE_GEOMETRY = No
    -> AttributeManager_77
AttributeManager_77
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfysvkn > bgt-fysiekvoorkomen
      RENAME_SET_VALUE plusfysvkn > plus-fysiekvoorkomen
      REMOVE fme_feature_type
      REMOVE bestandsnaam_plus
      REMOVE _count
      REMOVE hm_aand
    -> imgeo_extractie.vw_imgeo_scheiding01010000 (writer CSV_1)
Note: begroeidterrein: csv_gebied [CSV]
imgeo_extractie.vw_imgeo_scheiding01010000 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-fysiekvoorkomen auto, optalud text, plus-fysiekvoorkomen auto, geometrie float
GeometryExtractor_45
    ATTR = geometrie
    KIND_LONG = OGC Well Known Text
    OGCVERSION = 1.1
    OGC_WKT_PRECISION_DISPLAY = Shortened 64-bit
    REMOVE_GEOMETRY = No
    -> AttributeManager_85
AttributeManager_85
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      RENAME_SET_VALUE bgtfysvkn > bgt-fysiekvoorkomen
      RENAME_SET_VALUE plusfysvkn > plus-functie
      REMOVE fme_feature_type
      REMOVE bestandsnaam_plus
      REMOVE _count
      REMOVE hm_aand
    -> imgeo_extractie.vw_imgeo_scheiding0101000000 (writer CSV_1)
Note: Onbegroeidterrein: csv_gebied [CSV]
imgeo_extractie.vw_imgeo_scheiding0101000000 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgt-fysiekvoorkomen auto, optalud text, plus-functie auto, geometrie float
GeometryExtractor_46
    ATTR = geometrie
    KIND_LONG = OGC Well Known Text
    OGCVERSION = 1.1
    OGC_WKT_PRECISION_DISPLAY = Shortened 64-bit
    REMOVE_GEOMETRY = No
    -> AttributeManager_81
AttributeManager_81
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
      REMOVE fme_feature_type
      REMOVE bestandsnaam_plus
      REMOVE _count
      REMOVE hm_aand
    -> imgeo_extractie.vw_imgeo_scheiding010100000000 (writer CSV_1)
Note: Onsteund.waterdeel: csv_gebied [CSV]
imgeo_extractie.vw_imgeo_scheiding010100000000 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgttype text, plustype text, geometrie float
GeometryExtractor_47
    ATTR = geometrie
    KIND_LONG = OGC Well Known Text
    OGCVERSION = 1.1
    OGC_WKT_PRECISION_DISPLAY = Shortened 64-bit
    REMOVE_GEOMETRY = No
    -> AttributeManager_83
AttributeManager_83
    ATTR_TABLE:
      RENAME_SET_VALUE namespace > identificatie_namespace
      RENAME_SET_VALUE lokaalid > identificatie_lokaalid
      RENAME_SET_VALUE begintijd > objectbegintijd
      RENAME_SET_VALUE eindtijd > objecteindtijd
      RENAME_SET_VALUE tijdreg > tijdstipregistratie
      RENAME_SET_VALUE eindreg > eindregistratie
      RENAME_SET_VALUE lv_pubdat > lv-publicatiedatum
      RENAME_SET_VALUE bronhoud > bronhouder
      RENAME_SET_VALUE inonderzk > inonderzoek
      RENAME_SET_VALUE hoogtelig > relatievehoogteligging
      RENAME_SET_VALUE bgtstatus > bgt-status
      RENAME_SET_VALUE plusstatus > plus-status
    -> imgeo_extractie.vw_imgeo_scheiding01010000000000 (writer CSV_1)
Note: Waterdeel: csv_gebied [CSV]
imgeo_extractie.vw_imgeo_scheiding01010000000000 (writer CSV_1)
    attributes: identificatie_namespace auto, identificatie_lokaalid auto, objectbegintijd auto, objecteindtijd auto, tijdstipregistratie auto, eindregistratie auto, lv-publicatiedatum auto, bronhouder auto, inonderzoek auto, relatievehoogteligging auto, bgt-status auto, plus-status auto, bgttype text, plustype text, geometrie float

Bookmark: Esri_Shape per gebied
Note: : Esri_Shape_gebied [ESRISHAPE]
imgeo_extractie.vw_imgeo_kunstwerkdeel_point01 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), bgttype char(200), plustype char(200), hm_aand char(200)
Note: Funct.gebied: Esri_Shape_gebied [ESRISHAPE]
imgeo_extractie.vw_imgeo_kunstwerkdeel_point0100 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), bgttype char(200), plustype char(200), naam char(200)
Note: Punten
Note: : Esri_Shape_gebied [ESRISHAPE]
imgeo_extractie.vw_imgeo_kunstwerkdeel_point02 (writer ESRISHAPE_1)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
Note: Lijnen
Note: : Esri_Shape_gebied [ESRISHAPE]
imgeo_extractie.vw_imgeo_kunstwerkdeel_line00 (writer ESRISHAPE_1)
    attributes: namespace char(8), lokaalid char(38), begintijd date, einddtijd date, tijdreg char(20), eindreg char(20), lv_pubdat char(20), bronhoud char(40), inonderzk char(1), hoogtelig short, bgtstatus char(8), plusstatus char(8), bgttype char(200), plustype char(200)
Note: Vlakken
Note: : Esri_Shape_gebied [ESRISHAPE]
imgeo_extractie.vw_imgeo_kunstwerkdeel_polygon01 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), bgttype char(200), plustype char(200)
Note: Overbgrg.deel: shp_gebied [ESRISHAPE]
imgeo_extractie.vw_imgeo_kunstwerkdeel_point01000000000100000000 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), type char(200), hoortbij char(200), isbeweegb char(1)
Note: Overbrug.deel_pijler: shp_gebied [ESRISHAPE]
imgeo_extractie.vw_imgeo_kunstwerkdeel_point0100000000 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), type char(200), hoortbij char(200), isbeweegb char(1)
Note: Overbgrg.deel: shp_gebied [ESRISHAPE]
imgeo_extractie.vw_imgeo_kunstwerkdeel_point010000000001 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), type char(200), hoortbij char(200), isbeweegb char(1)
Note: Overbgrg.deel: shp_gebied [ESRISHAPE]
imgeo_extractie.vw_imgeo_kunstwerkdeel_point01000000000100 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), type char(200), hoortbij char(200), isbeweegb char(1)
Note: Overbgrg.deel: shp_gebied [ESRISHAPE]
imgeo_extractie.vw_imgeo_kunstwerkdeel_point0100000000010000 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), type char(200), hoortbij char(200), isbeweegb char(1)
Note: Overbgrg.deel: shp_gebied [ESRISHAPE]
imgeo_extractie.vw_imgeo_kunstwerkdeel_point010000000001000000 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), type char(200), hoortbij char(200), isbeweegb char(1)
Note: Tunneldeel: shp_gebied [ESRISHAPE]
imgeo_extractie.vw_imgeo_kunstwerkdeel_point010000 (writer ESRISHAPE_1)
    attributes: namespace char(8), lokaalid char(38), begintijd date, eindtijd char(200), tijdreg char(20), eindreg char(20), lv_pubdat char(20), bronhoud char(40), inonderzk char(1), hoogtelig short, bgtstatus char(8), plusstatus char(8)
Note: Spoor: shp_gebied [ESRISHAPE]
imgeo_extractie.vw_imgeo_kunstwerkdeel_point01000000 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), bgtfunctie char(200), plusfunct char(200)
Note: oongeclass: shp_gebied [ESRISHAPE]
imgeo_extractie.vw_imgeo_kunstwerkdeel_point010000000000 (writer ESRISHAPE_1)
    attributes: namespace char(8), lokaalid char(38), begintijd date, eindtijd char(200), tijdreg char(20), eindreg char(20), lv_pubdat char(20), bronhoud char(40), inonderzk char(1), hoogtelig short, bgtstatus char(8), plusstatus char(8)
Note: Pand: shp_gebied [ESRISHAPE]
imgeo_extractie.vw_imgeo_kunstwerkdeel_polygon0000 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), bagpndid char(20)
Note: rename hoortbij to biij_object
AttributeManager_38
    ATTR_TABLE = RENAME_SET_VALUE hoortbij > bij_object
    -> imgeo_extractie.vw_imgeo_kunstwerkdeel_polygon00 (writer ESRISHAPE_1)
Note: Kruinlijn: shp_gebied [ESRISHAPE]
imgeo_extractie.vw_imgeo_kunstwerkdeel_polygon00 (writer ESRISHAPE_1)
    attributes: namespace char(200), lokaalid char(38), begintijd date, eindtijd char(200), tijdreg char(20), eindreg char(20), lv_pubdat char(20), bronhoud char(40), inonderzk char(1), hoogtelig short, bgtstatus char(8), plusstatus char(8), optalud char(1), bij_object char(200)
AttributeKeeper_6
    KEEP_ATTRS = bagid,bestandsnaam,gebied
    -> imgeo_extractie.vw_imgeo_kunstwerkdeel_polygon000001 (writer ESRISHAPE_1)
    -> GeometryExtractor_14
Note: BAG_Standplaats: shp_gebied [ESRISHAPE]
imgeo_extractie.vw_imgeo_kunstwerkdeel_polygon000001 (writer ESRISHAPE_1)
    attributes: bagid char(20)
AttributeKeeper_5
    KEEP_ATTRS = bagid,bestandsnaam,gebied
    -> imgeo_extractie.vw_imgeo_kunstwerkdeel_polygon0001 (writer ESRISHAPE_1)
    -> GeometryExtractor_9
Note: BAG_Ligplaats: shp_gebied [ESRISHAPE]
imgeo_extractie.vw_imgeo_kunstwerkdeel_polygon0001 (writer ESRISHAPE_1)
    attributes: bagid char(20)
AttributeKeeper_7
    KEEP_ATTRS = gebied,eindreg,bestandsnaam,guid,hoogtelig
    -> imgeo_extractie.vw_imgeo_kunstwerkdeel_polygon00000001 (writer ESRISHAPE_1)
    -> GeometryExtractor_15
Note: Overbouw: Esri_Shape_gebied [ESRISHAPE]
imgeo_extractie.vw_imgeo_kunstwerkdeel_polygon00000001 (writer ESRISHAPE_1)
    attributes: eindreg char(20), hoogtelig short, guid char(38)
AttributeKeeper_8
    KEEP_ATTRS = guid,hoogtelig,bestandsnaam,gebied,eindreg
    -> imgeo_extractie.vw_imgeo_kunstwerkdeel_polygon0000000000 (writer ESRISHAPE_1)
    -> GeometryExtractor_16
Note: Onderbouw: Esri_Shape_gebied [ESRISHAPE]
imgeo_extractie.vw_imgeo_kunstwerkdeel_polygon0000000000 (writer ESRISHAPE_1)
    attributes: eindreg char(20), hoogtelig short, guid char(38)
Note: Openbareruimte: shp_gebied [ESRISHAPE]
imgeo_extractie.vw_imgeo_kunstwerkdeel_point0000 (writer ESRISHAPE_1)
    attributes: namespace char(8), lokaalid char(38), begintijd date, einddtijd date, tijdreg char(20), eindreg char(20), lv_pubdat char(20), bronhoud char(40), inonderzk char(1), hoogtelig short, bgtstatus char(8), plusstatus char(8), bagoprid char(20), oprtype char(200), hoek float, tekst char(200)
Note: huisnrs: shp_gebied [ESRISHAPE]
imgeo_extractie.vw_imgeo_kunstwerkdeel_point00 (writer ESRISHAPE_1)
    attributes: lokaalid char(38), bagpndid char(20), tekst char(200), tekst_afk char(200), bagvbolgst char(20), bagvbohgst char(20), hoek float
Note: Wegdeel: shp_gebied [ESRISHAPE]
imgeo_extractie.vw_imgeo_kunstwerkdeel_point0001 (writer ESRISHAPE_1)
    attributes: namespace char(8), lokaalid char(38), begintijd date, einddtijd date, tijdreg char(20), eindreg char(20), lv_pubdat char(20), bronhoud char(40), inonderzk char(1), hoogtelig short, bgtstatus char(8), plusstatus char(8), bgtfunctie char(200), bgtfysvkn char(200), optalud char(1), plusfunct char(200), plusfysvkn char(200)
Note: Wegdeel: shp_gebied [ESRISHAPE]
imgeo_extractie.vw_imgeo_kunstwerkdeel_point000100 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), bgtfunctie char(200), bgtfysvkn char(200), optalud char(1), plusfunct char(200), plusfysvkn char(200)
Note: Begroeidterrein: shp_gebied [ESRISHAPE]
imgeo_extractie.vw_imgeo_kunstwerkdeel_point00010000 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), bgtfysvkn char(200), optalud char(1), plusfysvkn char(200)
Note: Onbegroeidterrein: shp_gebied [ESRISHAPE]
imgeo_extractie.vw_imgeo_kunstwerkdeel_point0001000000 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), bgtfysvkn char(200), optalud char(1), plusfysvkn char(200)
Note: Ondersteund.waterdeel: shp_gebied [ESRISHAPE]
imgeo_extractie.vw_imgeo_kunstwerkdeel_point000100000000 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), bgttype char(200), plustype char(200)
Note: Waterdeel: shp_gebied [ESRISHAPE]
imgeo_extractie.vw_imgeo_kunstwerkdeel_point00010000000000 (writer ESRISHAPE_1)
    attributes: namespace char(8), lokaalid char(38), begintijd date, eindtijd char(200), tijdreg char(20), eindreg char(20), lv_pubdat char(20), bronhoud char(40), inonderzk char(1), hoogtelig short, bgtstatus char(8), plusstatus char(8), bgttype char(200), plustype char(200)

Bookmark: labels_BAG_standplaatsen
Note: lps-nraanduiding: shp_gebied [ESRISHAPE]
bestandsnaam000000 (writer ESRISHAPE_1)
    attributes: bagid char(20), adres char(254), tekst char(10), hoek float
GeometryExtractor_61
    ATTR = geometrie
    KIND_LONG = OGC Well Known Text
    OGCVERSION = 1.1
    OGC_WKT_PRECISION_DISPLAY = Shortened 64-bit
    REMOVE_GEOMETRY = No
    -> AttributeManager_117
AttributeManager_117
    ATTR_TABLE:
      RENAME_SET_VALUE bagid > BAG_identificatie
      REMOVE eindreg
      REMOVE hoogtelig
      REMOVE fme_feature_type
      REMOVE namespace
      REMOVE lokaalid
      REMOVE begintijd
      REMOVE einddtijd
      REMOVE tijdreg
      REMOVE lv_pubdat
      REMOVE bronhoud
      REMOVE inonderzk
      REMOVE bgtstatus
      REMOVE plusstatus
      REMOVE bgttype
      REMOVE plustype
      REMOVE bestandsnaam_plus
      REMOVE eindtijd
      REMOVE _count
      REMOVE type
      REMOVE hoortbij
      REMOVE isbeweegb
      REMOVE optalud
      REMOVE bgtfunctie
      REMOVE bgtfysvkn
      REMOVE plusfunct
      REMOVE plusfysvkn
      REMOVE tekst_afk
      REMOVE bagpndid
      REMOVE bagvbolgst
      REMOVE bagvbohgst
      REMOVE bagoprid
      REMOVE oprtype
      REMOVE hm_aand
      REMOVE guid
    -> imgeo_extractie.vw_imgeo_scheiding000100000000 (writer CSV_1)
Note: sps_nraanduiding: csv_gebied [CSV]
imgeo_extractie.vw_imgeo_scheiding000100000000 (writer CSV_1)
    attributes: BAG_identificatie auto, adres text, tekst text, hoek float, geometrie auto

Bookmark: Labels_BAG_ligplaatsen
GeometryExtractor_62
    ATTR = geometrie
    KIND_LONG = OGC Well Known Text
    OGCVERSION = 1.1
    OGC_WKT_PRECISION_DISPLAY = Shortened 64-bit
    REMOVE_GEOMETRY = No
    -> AttributeManager_120
AttributeManager_120
    ATTR_TABLE:
      RENAME_SET_VALUE bagid > BAG_identificatie
      REMOVE fme_feature_type
      REMOVE eindreg
      REMOVE hoogtelig
      REMOVE namespace
      REMOVE lokaalid
      REMOVE begintijd
      REMOVE einddtijd
      REMOVE tijdreg
      REMOVE lv_pubdat
      REMOVE bronhoud
      REMOVE inonderzk
      REMOVE bgtstatus
      REMOVE plusstatus
      REMOVE bgttype
      REMOVE plustype
      REMOVE bestandsnaam_plus
      REMOVE eindtijd
      REMOVE _count
      REMOVE type
      REMOVE hoortbij
      REMOVE isbeweegb
      REMOVE optalud
      REMOVE bgtfunctie
      REMOVE bgtfysvkn
      REMOVE plusfunct
      REMOVE plusfysvkn
      REMOVE tekst_afk
      REMOVE bagpndid
      REMOVE bagvbolgst
      REMOVE bagvbohgst
      REMOVE bagoprid
      REMOVE oprtype
      REMOVE hm_aand
      REMOVE guid
    -> imgeo_extractie.vw_imgeo_scheiding00010000000001 (writer CSV_1)
Note: lbl_Ligplaats: csv_totaal [CSV]
imgeo_extractie.vw_imgeo_scheiding00010000000001 (writer CSV_1)
    attributes: BAG_identificatie auto, adres text, tekst text, hoek float, geometrie auto
Note: lps-nraanduiding: shp_totaal [ESRISHAPE]
bestandsnaam00000000 (writer ESRISHAPE_1)
    attributes: bagid char(20), adres char(254), tekst char(10), hoek float

Bookmark: Bepalen multi polygone en polygon
PartCounter_2
    RECURSIVE_PARAM = No
    COUNT_ATTR = _part_count
    -> Tester_2
Tester_2
    TEST_MODE = Automatic
    TEST_CLAUSE = TEST @Value(_part_count) = 1
    TEST_DESCRIPTION = ""
    BOOL_OP = OR
    PASSED -> Deaggregator_2
    FAILED -> GeometryExtractor_26
Deaggregator_2
    CHILD_ID_ATTR = _hierarchy_child_id_list
    GEOM_NAME_FIELD = _geometry_name
    ID_ATTR = _hierarchy_id
    PARENT_ID_ATTR = _hierarchy_parent_id
    EXPLODE_INSTANCES = No
    LIST_ATTR_MODE_LOOKUP = LEAN
    COPY_ATTR = Every Node
    ID_SELECTION = ID and Parent ID
    MODE = Flatten One Level
    SPLIT_COMPOSITES = No
    PART_NUMBER_FIELD = _part_number
    DEAGGREGATED -> GeometryExtractor_26
