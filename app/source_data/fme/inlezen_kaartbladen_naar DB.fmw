FME workspace inlezen_kaartbladen_naar DB.fmw

Parameters:
- bron_BGT_kaartbladen = C:\datapunt\code\BGT\app\source_data\bron_shapes\BGT_kaartbladen.shp   # BGT_kaartbladen
- SourceDataset_WFS = https://geodata.nationaalgeoregister.nl/bestuurlijkegrenzen/wfs?   # Source WFS (Web Feature Service) URL
- SourceDataset_WFS_3 = https://map.data.amsterdam.nl/maps/gebieden?REQUEST=GetCapabilities&SERVICE=wfs   # Source WFS (Web Feature Service) URL
- DestDataset_ESRISHAPE = $(FME_MF_DIR)kaartindeling   # Destination Esri Shapefile Folder
- DestDataset_DGNV8 = $(FME_MF_DIR)kaartindeling\PDOK_Indeling.dgn   # Destination Bentley MicroStation Design File
- DestDataset_POSTGIS_4 = bgt_dev_local   # Connection

Readers:
- ESRISHAPE_1: ESRISHAPE from $(bron_BGT_kaartbladen) in EPSG:28992
- WFS_1: WFS from $(SourceDataset_WFS)
- WFS_2: WFS from $(SourceDataset_WFS_3)

Writers:
- ESRISHAPE_2: ESRISHAPE to $(DestDataset_ESRISHAPE) in EPSG:28992
- DGNV8_1: DGNV8 to $(DestDataset_DGNV8)
- POSTGIS_1: POSTGIS to $(DestDataset_POSTGIS_4) in EPSG:28992

Note: stadsdeel: gebieden [WFS]
stadsdeel (reader WFS_2)
    attributes: gml_parent_id xml_buffer, gml_parent_property xml_buffer, gml_id xml_buffer, msGeometry xml_geometry, id xml_buffer, code xml_buffer, naam xml_buffer, display xml_buffer, type xml_buffer, uri xml_buffer
    -> AttributeManager_2
Note: verwijder overbodigheden en hernoem met prefix
AttributeManager_2
    ATTR_TABLE:
      REMOVE gml_parent_id
      REMOVE gml_parent_property
      REMOVE gml_id
      REMOVE msGeometry
      REMOVE id
      REMOVE code
      SET_TO naam > NAAM = Amsterdam_@Value(naam)
      REMOVE display
      REMOVE type
      REMOVE uri
      SET_TO big_id = 2
    -> Tester_2
Note: voor nieuwwest een uizondering maken. vanwege liggend streepje
Tester_2
    TEST_MODE = Automatic
    BOOL_OP = OR
    TEST_DESCRIPTION = ""
    TEST_CLAUSE = TEST @Value(naam) = Nieuw-West
    PASSED -> AttributeManager
    FAILED -> StringReplacer_2
AttributeManager
    ATTR_TABLE = SET_TO NAAM = Amsterdam_Nieuwwest
    -> StringReplacer_2
Note: leestekens in namen weghalen
StringReplacer_2
    REPLACE_TEXT = _
    CASE = NO
    NO_MATCH = _FME_NO_OP_
    FIND_TEXT = " "
    REGEXP = NO
    SRC_ATTRS = NAAM
    -> StringReplacer_3
StringReplacer_3
    CASE = NO
    NO_MATCH = _FME_NO_OP_
    FIND_TEXT = -
    REGEXP = NO
    SRC_ATTRS = NAAM
    -> AttributeKeeper
AttributeKeeper
    KEEP_ATTRS = NAAM,big_id
    -> TopologyBuilder
Note: gemeenten: nationaal georegister [WFS], heel nederland
gemeenten (reader WFS_1)
    attributes: gml_parent_id xml_buffer, gml_parent_property xml_buffer, gml_id xml_buffer, code xml_buffer, code.xsi_nil xml_boolean, gemeentenaam xml_buffer, gemeentenaam.xsi_nil xml_boolean, geom xml_geometry
    -> AttributeManager_GME_3
Note: verwijder overbodigheden en rename attr
AttributeManager_GME_3
    ATTR_TABLE:
      SET_TO big_id = 2
      REMOVE gml_id
      REMOVE code
      REMOVE gml_parent_id
      REMOVE gml_parent_property
      REMOVE code.xsi_nil
      RENAME_SET_VALUE gemeentenaam > NAAM
      REMOVE gemeentenaam.xsi_nil
      REMOVE geom
    -> StringReplacer_5
Note: leestekens in namen weghalen
StringReplacer_5
    CASE = NO
    NO_MATCH = _FME_NO_OP_
    FIND_TEXT = '
    REGEXP = NO
    SRC_ATTRS = NAAM
    -> StringReplacer
StringReplacer
    REPLACE_TEXT = _
    CASE = NO
    NO_MATCH = _FME_NO_OP_
    FIND_TEXT = " "
    REGEXP = NO
    SRC_ATTRS = NAAM
    -> StringReplacer_4
StringReplacer_4
    CASE = NO
    NO_MATCH = _FME_NO_OP_
    FIND_TEXT = -
    REGEXP = NO
    SRC_ATTRS = NAAM
    -> Tester_3
Note: haal amsterdam eruit, / die komt via de andere lijn
Tester_3
    TEST_MODE = Automatic
    BOOL_OP = OR
    TEST_DESCRIPTION = ""
    TEST_CLAUSE = TEST @Value(NAAM) = Amsterdam
    FAILED -> TopologyBuilder
Note: mogelijke geometrische verschillen verwijderen
TopologyBuilder
    DEAGGREGATE_INPUT = Yes
    PROP_ATTRS = No
    BOUNDING_EDGES = All
    MAX = 0
    OVERLAPPING_MODE = No
    CLEAN_DATA = No
    ALLOW_CYCLES = No
    AREA -> Clipper [input 2]
Note: BGT_kaartbladen [ESRISHAPE]
BGT_kaartbladen (reader ESRISHAPE_1)
    attributes: Tegelindex short, Bladnaam char(13)
    -> AttributeManager_kbd
Note: verwijder overbodige kenmerken en rename
AttributeManager_kbd
    ATTR_TABLE:
      REMOVE Tegelindex
      SET_TO big_id = 1
    -> Tester
    -> Dissolver
Note: voeg alle bladen samen / en buffer, om max gebied / te bepalen voor gebieden
Dissolver
    GROUP_BY = big_id
    NO_OVRLP = No
    CONNECT_Z_MODE = First Wins
    ACCUM_INPUT_ATTRS = No
    AREA -> Bufferer
Bufferer
    INTERP_SEGMENTS = 8
    OFFSET = 5000
    CAP_STYLE = Round
    BUFFERED -> Clipper [input 1]
Note: uitsnijden naar max gebied
Clipper
    CREATE_AGGREGATES = Yes
    CLIPPED_ATTR = _clipped
    CLIP_TYPE = Multiple Clippers
    BOUNDARY_CASES = Treat as Inside
    CONNECT_Z_MODE = First Wins
    PRESERVE_CLIPPEE_EXTENTS = No
    LINES_AS_SEGMENTS = No
    INSIDE -> imgeo.pdt_kaartblad (writer POSTGIS_1)
    INSIDE -> BGT_Gebiedsindeling (writer ESRISHAPE_2)
Note: alleen gevulde kaartbladen door
Tester
    TEST_MODE = Automatic
    BOOL_OP = OR
    TEST_DESCRIPTION = ""
    TEST_CLAUSE = TEST @Value(Bladnaam) ATTRIBUTE_HAS_VALUE ""
    PASSED -> Kaartbladen (writer DGNV8_1)
    PASSED -> CenterPointReplacer
    PASSED -> imgeo.pdt_kaartblad (writer POSTGIS_1)
CenterPointReplacer
    MODE = Center Point
    POINT -> LabelPointReplacer_2
LabelPointReplacer_2
    ALWAYSROTATE = yes
    LABATTR = @Value(Bladnaam)
    HEIGHT = 10
    LabelPoint -> Bladnummers (writer DGNV8_1)

Bookmark: Shape
BGT_Gebiedsindeling (writer ESRISHAPE_2)
    attributes: naam char(200)

Bookmark: Postgres
imgeo.pdt_kaartblad (writer POSTGIS_1)
    attributes: naam varchar(200), big_id int4

Bookmark: dgn
Kaartbladen (writer DGNV8_1)
Bladnummers (writer DGNV8_1)
