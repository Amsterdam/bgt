FME workspace over_onderbouw2postgres.fmw

Parameters:
- SourceDataset_ORACLE_SPATIAL_3 = DBIGKP01   # Service Name or Easy Connect
- DestDataset_POSTGIS = bgt_dev_local   # Connection
- DestDataset_POSTGIS_6 = bgt_dev_local   # Connection

Readers:
- ORACLE_SPATIAL_1: ORACLE_SPATIAL from $(SourceDataset_ORACLE_SPATIAL_3)

Writers:
- POSTGIS_1: POSTGIS to $(DestDataset_POSTGIS) in EPSG:28992
- POSTGIS_2: POSTGIS to $(DestDataset_POSTGIS_6) in EPSG:28992

Bookmark: Inlezen overbouw in postgresdatabase
Note: BGT.DGDTW_TOPOGRAFIE: DBIGKP01 [objectcode=612] / userproxy: BGT_PROXY
BGT.DGDTW_TOPOGRAFIE (reader ORACLE_SPATIAL_1)
    attributes: ID number(20,0), OBJECTCODE number(5,0), PARAMETERS number(5,0), BRON number(5,0), INWIN date, VERVAL date, LOCKNR number, XMLATTRIBUTEN clob, NIVO number(5,0), GTABLE number(6,0), GUID varchar2(38), LOKAAL_ID varchar2(42), OBJECTBEGINTIJD date, TIJDSTIP_REGISTRATIE date
    -> Tester_4
Note: bepalen actuele objecten
Tester_4
    TEST_DESCRIPTION = ""
    TEST_CLAUSE = TEST VERVAL ATTRIBUTE_VALUE_NULL ""
    TEST_MODE = Automatic
    BOOL_OP = OR
    PASSED -> Tester_5
Note: Bepalen overbouw
Tester_5
    TEST_DESCRIPTION = ""
    TEST_CLAUSE = TEST @Value(NIVO) > 0
    TEST_MODE = Automatic
    BOOL_OP = OR
    PASSED -> AttributeManager_52
    FAILED -> AttributeManager_2
AttributeManager_52
    ATTR_TABLE:
      REMOVE ID
      REMOVE OBJECTCODE
      REMOVE PARAMETERS
      REMOVE BRON
      REMOVE INWIN
      RENAME_SET_VALUE VERVAL > eindregistratie
      REMOVE LOCKNR
      REMOVE XMLATTRIBUTEN
      RENAME_SET_VALUE NIVO > relatievehoogteligging
      REMOVE GTABLE
      REMOVE GUID
      REMOVE LOKAAL_ID
      REMOVE OBJECTBEGINTIJD
      REMOVE TIJDSTIP_REGISTRATIE
      SET_TO bestandsnaam = CFT_Overbouw
    -> imgeo.CFT_Overbouw (writer POSTGIS_1)
imgeo.CFT_Overbouw (writer POSTGIS_1)
    attributes: eindregistratie date, relatievehoogteligging int2, bestandsnaam varchar(15)
AttributeManager_2
    ATTR_TABLE:
      REMOVE ID
      REMOVE OBJECTCODE
      REMOVE PARAMETERS
      REMOVE BRON
      REMOVE INWIN
      RENAME_SET_VALUE VERVAL > eindregistratie
      REMOVE LOCKNR
      REMOVE XMLATTRIBUTEN
      RENAME_SET_VALUE NIVO > relatievehoogteligging
      REMOVE GTABLE
      REMOVE GUID
      REMOVE LOKAAL_ID
      REMOVE OBJECTBEGINTIJD
      REMOVE TIJDSTIP_REGISTRATIE
      SET_TO bestandsnaam = CFT_Onderbouw
    -> imgeo.CFT_Onderbouw (writer POSTGIS_2)
imgeo.CFT_Onderbouw (writer POSTGIS_2)
    attributes: eindregistratie date, relatievehoogteligging int2, bestandsnaam varchar(15)
