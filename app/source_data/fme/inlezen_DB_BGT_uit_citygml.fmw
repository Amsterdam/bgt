FME workspace inlezen_DB_BGT_uit_citygml.fmw

Parameters:
- DestDataset_POSTGIS_4 = bgt_dev_local   # Connection
- SourceDataset_CITYGML = C:\Users\Barney\Downloads\bgt_functioneelgebied.gml   # Source CityGML File(s)
- CITYGML_IN_ADE_XSD_DOC_CITYGML = C:\BGT\code\app\source_data\xsd\imgeo.xsd   # Additional ADE Schema File(s)
- DestDataset_POSTGIS = bgt_dev_local   # Connection

Readers:
- CITYGML_1: CITYGML from $(SourceDataset_CITYGML) in EPSG:28992

Writers:
- POSTGIS_1: POSTGIS to $(DestDataset_POSTGIS_4) in EPSG:28992
- POSTGIS_2: POSTGIS to $(DestDataset_POSTGIS) in EPSG:28992

Note: ListExploder_hoortbijtypeoverbrugging
ListExploder_hoortbijtypeoverbrugging
    LIST_ATTR = hoortbijtypeoverbrugging{}
    ATTR_CONFLICT_RES = Use Incoming List
    ATTR_ACCUM_MODE = Merge Incoming List
    INDEX_ATTR = _element_index
    ELEMENTS -> ListExploder_overbruggingbeweegbaar
    <REJECTED> -> ListExploder_overbruggingbeweegbaar
Note: ListExploder_overbruggingbeweegbaar
ListExploder_overbruggingbeweegbaar
    LIST_ATTR = overbruggingisbeweegbaar{}
    ATTR_CONFLICT_RES = Use Incoming List
    ATTR_ACCUM_MODE = Merge Incoming List
    INDEX_ATTR = _element_index
    ELEMENTS -> Verwijder_attributen_uit_Listexploders_en_zet_attributen_volgens_definitie__in_onderzoek_en_plus-status__18
    <REJECTED> -> Verwijder_attributen_uit_Listexploders_en_zet_attributen_volgens_definitie__in_onderzoek_en_plus-status__18
Note: ListExploder_plusType_gebouwinstallatie
ListExploder_plusType_gebouwinstallatie
    LIST_ATTR = plus_type{}
    ATTR_CONFLICT_RES = Use Incoming List
    ATTR_ACCUM_MODE = Merge Incoming List
    INDEX_ATTR = _element_index
    ELEMENTS -> Verwijder_attributen_uit_Listexploders_en_zet_attributen_volgens_definitie__in_onderzoek_en_plus-status__19
    <REJECTED> -> Verwijder_attributen_uit_Listexploders_en_zet_attributen_volgens_definitie__in_onderzoek_en_plus-status__19
OpenbareRuimteLabelExtractor
    IMGEO_OPENBARE_RUIMTE_NAAM = @Value(imgeo_openbare_ruimte_naam)
    GeometryReplacer_labelpos_Output -> Verwijder_overbodige_attributen_33
ListExploder
    LIST_ATTR = imgeo_nummeraanduidingreeks{}
    ATTR_CONFLICT_RES = Use Incoming List
    ATTR_ACCUM_MODE = Merge Incoming List
    INDEX_ATTR = _num_index
    ELEMENTS -> Huisnummerlabeler
Huisnummerlabeler
    GML_ID = @Value(gml_id)
    IMGEO_NUMMERAANDUIDINGREEKS_IMGEO_IDENTIFICATIE_BAGVBOHOOGSTE_HUISNUMMER = @Value(imgeo_nummeraanduidingreeks_imgeo_identificatie_bagvbohoogste_huisnummer)
    IMGEO_NUMMERAANDUIDINGREEKS_IMGEO_IDENTIFICATIE_BAGVBOLAAGSTE_HUISNUMMER = @Value(imgeo_nummeraanduidingreeks_imgeo_identificatie_bagvbolaagste_huisnummer)
    OBJECTEINDTIJD = @Value(objecteindtijd)
    _NUM_INDEX = @Value(_num_index)
    IMGEO_NUMMERAANDUIDINGREEKS_IMGEO_NUMMERAANDUIDINGREEKS = @Value(imgeo_nummeraanduidingreeks_imgeo_nummeraanduidingreeks)
    OBJECTBEGINTIJD = @Value(objectbegintijd)
    GeometryReplacer_Output -> Generieke_attributen_31
Note: ListExploder_identificatiebagpnd
ListExploder_identificatiebagpnd_2
    LIST_ATTR = identificatiebagpnd{}
    ATTR_CONFLICT_RES = Use Incoming List
    ATTR_ACCUM_MODE = Merge Incoming List
    INDEX_ATTR = _element_index
    ELEMENTS -> Verwijder_attributen_uit_Listexploders_en_zet_attributen_volgens_definitie__in_onderzoek_en_plus-status__32
    <REJECTED> -> Verwijder_attributen_uit_Listexploders_en_zet_attributen_volgens_definitie__in_onderzoek_en_plus-status__32
Note: ListExploder:_list
ListExploder:_list
    LIST_ATTR = _list{}
    ATTR_CONFLICT_RES = Use Incoming List
    ATTR_ACCUM_MODE = Merge Incoming List
    INDEX_ATTR = _element_index
    ELEMENTS -> StringReplacer
Note: StringReplacer: spatie verwijderen ivm spatie in reeks (Purmerend)
StringReplacer
    REGEXP = NO
    NO_MATCH = _FME_NO_OP_
    FIND_TEXT = " "
    CASE = NO
    SRC_ATTRS = _list
    -> StringSearcher_6
Note: Zoek in de _list naar getallen (=huisnsrs) en letters (huisletters) en zet het in _list2 / NB getallen en letters met een spatie worden ook meegenomen: / 1 / A / 2 (met spatie) / B (met spatie)
StringSearcher_6
    REGEXP = ^([0-9]*)([A-Z ]*)
    STRING_TO_SEARCH = @Value(_list)
    MATCHED_RESULT_ATTR = _first_match
    CASE = no
    MATCHED_PARTS_ATTR = _list2
    MATCHED -> ListExploder_4
Note: Hierbij worden de getallen en letters teruggegeven en in list_2.part geplaatst. / NB alle andere tekens /* (=huisnummertoevoegingen) worden buitenbeschouw gelaten en dus niet teruggegeven. / bv 48/H-48B wordt in attribuut part uitgesplitst in 4 records: / 48 / null (omdat /H niet wordt gezocht en dus niks teruggeeft) / 48 / B
ListExploder_4
    LIST_ATTR = _list2{}
    ATTR_CONFLICT_RES = Use Incoming List
    ATTR_ACCUM_MODE = Merge Incoming List
    INDEX_ATTR = _element_index_2
    ELEMENTS -> AttributeManager
Note: Er worden twee nieuwe attributen, huisnummer en huisletter toegevoegd: / - huisnummer: Als part van het type een getal is, is dit een huisnummer. / - huisletter: Als part niet van het type getal is dus geen getal, is dit dus een huisletter.
AttributeManager
    ATTR_TABLE:
      SET_TO huisnummer = FME_CONDITIONAL:DEFAULT_VALUE'_FME_NO_OP_'BOOL_OP;AND;COMPOSITE_TEST;<Unused>;TEST @Value(part) TYPE NUM'@Value(part)'FME_NUM_CONDITIONS2___
      SET_TO huisletter = FME_CONDITIONAL:DEFAULT_VALUE'@Value(part)'BOOL_OP;OR;COMPOSITE_TEST;<Unused>;TEST @Value(part) TYPE NUM''FME_NUM_CONDITIONS2___
    -> Tester_4
Note: Huisnummerreeksen: afgekorte teksten / ==================================== / De huisnummerreeksen (feature: BGT_LBL_nummeraanduidingreeks) bevatten in de kolom 'tekst' de landelijk gehanteerde schrijfwijze. Zie ook http://www.geonovum.nl/sites/default/files/20150716_BGT-werkafspraak-nummeraanduidingreeksen_def_0.pdf: / " / Voor de opmaak van een NAR dient zo veel mogelijk onderstaand patroon toegepast te worden. / {huisnummer}{huisletter}/{huisnummertoevoeging}-{huisnummer}{huisletter}/{huisnummertoevoeging} / waarin / {huisnummer} een nummer van 1 tot 99999 (regex {0-9}[1-5]) / {huisletter} een hoofdletter of kleine letter (regex {a-zA-Z}[0-1]) / {huisnummertoevoeging} 0 tot 4 alfanumeriek karakter (regex {0-9a-zA-Z}[0-4]) / en verder / * Geen scheidingsteken tussen huisnummer en huisletter, dus geen koppelteken (-) en geen spatie. / * Scheidingsteken tussen huisnummer+huisletter en huisnummertoevoeging is een forward slash (/). / * Nummeraanduidingen (=combinatie van huisnummer, huisletter en/of huisnummertoevoeging) worden gescheiden door een koppelteken (-). / Dus bijvoorbeeld: 33, 33A, 33/1, 33-37, 33A-33F, 33/1-33/20, 33A/1–33A/20, 33A/1A-33A/3F. / " / Als huisnummerreeksen met deze notatiewijze op een kaart worden afgebeeld geeft dat in veel gevallen een te druk kaartbeeld. De kans op overlappende huisnummer is groot. / Daarom levert BI ook een afgekorte versie mee waarin dubbele voorkomens van de combinatie {huisnummer}{huisletter}/{huisnummertoevoeging} worden weggelaten: / BGT afkorting patroon BGT patroon afgekort / --------------- --------- --------------------------------------------------------------------------------------------------- ---------------------------------------------------------------------- / geen koppelteken: / 33 33 {huisnummer} geen wijziging / 33A 33A {huisnummer}{huisletter} geen wijziging / 33/1 33/1 {huisnummer}/{huisnummertoevoeging} geen wijziging / koppelteken, gelijke {huisnummer} / 33A-33F 33A-F {huisnummer}{huisletter}-{huisnummer}{huisletter} {huisnummer}{huisletter}-{huisletter} / 33/1-33/20 33 {huisnummer}/{huisnummertoevoeging}-{huisnummer}/{huisnummertoevoeging} {huisnummer}{huisletter}-{huisletter} / 33A/1–33A/20 33A {huisnummer}{huisletter}/{huisnummertoevoeging}-{huisnummer}{huisletter}/{huisnummertoevoeging} {huisnummer}{huisletter}-{huisletter} / 33A/1A-33A/3F 33A {huisnummer}{huisletter}/{huisnummertoevoeging}-{huisnummer}{huisletter}/{huisnummertoevoeging} {huisnummer}{huisletter}-{huisletter} / koppelteken, ongelijke {huisnummer} / 33-37 33-37 {huisnummer}-{huisnummer} {huisnummer}-{huisnummer} / 33A-37C 33-37 {huisnummer}{huisletter}-{huisnummer}{huisletter} {huisnummer}-{huisnummer} / 33/1-37/20 33-37 {huisnummer}/{huisnummertoevoeging}-{huisnummer}/{huisnummertoevoeging} {huisnummer}-{huisnummer} / 33A/1-37C/20 33-37 {huisnummer}{huisletter}/{huisnummertoevoeging}-{huisnummer}{huisletter}/{huisnummertoevoeging} {huisnummer}-{huisnummer} / 33A/1A-37C/3F 33-37 {huisnummer}{huisletter}/{huisnummertoevoeging}-{huisnummer}{huisletter}/{huisnummertoevoeging} {huisnummer}-{huisnummer}
Matcher_gelijke_huisnummer
    MATCH_STRATEGY = Match Selected Attributes
    LENIENT_MATCH = No
    MATCH = 2D
    CNT_ATTR = _match_id
    BLANK_AND_MISSING_DIFFER = No
    DIFFATTRS = _element_index
    SM_LIST_NAME = lijst3
    MATCHATTRS = identificatie_lokaalid huisnummer
    NOT_MATCHED -> Matcherongelijkhuisnummers
    SINGLE_MATCHED -> TesterHuisletterIsGevuld
imgeo.bgt_nummeraanduidingreeks (writer POSTGIS_2)
    attributes: objectbegintijd date, objecteindtijd date, eindregistratie date, bronhouder varchar(40), tijdstipregistratie date, inonderzoek varchar(1), relatievehoogteligging int2, lv_publicatiedatum date, bgt_status varchar(8), plus_status varchar(8), identificatie_namespace varchar(8), tekst varchar(200), tekst_afgekort varchar(200), hnr_label_hoek float4, identificatie_lokaalid varchar(38), identificatieBAGVBOLaagsteHuisnummer varchar(20), identificatieBAGVBOHoogsteHuisnummer varchar(20), identificatieBAGPND varchar(20)
Note: ListExploder_identificatiebagpnd
ListExploder_identificatiebagpnd
    LIST_ATTR = identificatiebagpnd{}
    ATTR_CONFLICT_RES = Use Incoming List
    ATTR_ACCUM_MODE = Merge Incoming List
    INDEX_ATTR = _element_index
    ELEMENTS -> Verwijder_attributen_uit_Listexploders_en_zet_attributen_volgens_definitie__in_onderzoek_en_plus-status_
    <REJECTED> -> Verwijder_attributen_uit_Listexploders_en_zet_attributen_volgens_definitie__in_onderzoek_en_plus-status_
Deaggregator_4
    SPLIT_COMPOSITES = No
    GEOM_NAME_FIELD = _geometry_name
    EXPLODE_INSTANCES = No
    MODE = Flatten One Level
    PART_NUMBER_FIELD = _part_number
    LIST_ATTR_MODE_LOOKUP = LEAN
    DEAGGREGATED -> GeometryFilter_wegdeel
GeometryFilter_wegdeel
    GEOM_PORT_NAMES = Line Area
    BREAK_AGG = No
    LINE -> Verwijder_overbodige_attributen_39
    AREA -> Verwijder_overbodige_attributen_29
AttributeManager_7
    ATTR_TABLE:
      REMOVE _element_index
      REMOVE fme_rejection_code
      SET_TO horend_bij = wegdeel
      REMOVE _opTalud_index
    -> Verwijder_attributen_uit_Listexploders_en_zet_attributen_volgens_definitie__in_onderzoek_en_plus-status__36
Deaggregator_3
    SPLIT_COMPOSITES = No
    GEOM_NAME_FIELD = _geometry_name
    EXPLODE_INSTANCES = No
    MODE = Flatten One Level
    PART_NUMBER_FIELD = _part_number
    LIST_ATTR_MODE_LOOKUP = LEAN
    DEAGGREGATED -> GeometryFilter_ondersteunendWegdeel
GeometryFilter_ondersteunendWegdeel
    GEOM_PORT_NAMES = Line Area
    BREAK_AGG = No
    LINE -> Verwijder_overbodige_attributen_38
    AREA -> Verwijder_overbodige_attributen_34
AttributeManager_5
    ATTR_TABLE:
      REMOVE _element_index
      REMOVE fme_rejection_code
      SET_TO horend_bij = ondersteunend wegdeel
    -> Verwijder_attributen_uit_Listexploders_en_zet_attributen_volgens_definitie__in_onderzoek_en_plus-status__36
Deaggregator
    SPLIT_COMPOSITES = No
    GEOM_NAME_FIELD = _geometry_name
    EXPLODE_INSTANCES = No
    MODE = Flatten One Level
    PART_NUMBER_FIELD = _part_number
    LIST_ATTR_MODE_LOOKUP = LEAN
    DEAGGREGATED -> GeometryFilter_begroeidTerreindeel
GeometryFilter_begroeidTerreindeel
    GEOM_PORT_NAMES = Line Area
    BREAK_AGG = No
    LINE -> Verwijder_overbodige_attributen_kruinlijn
    AREA -> Verwijder_overbodige_attributen_36
AttributeManager_8
    ATTR_TABLE:
      REMOVE _element_index
      REMOVE fme_rejection_code
      SET_TO horend_bij = begroeid terreindeel
    -> Verwijder_attributen_uit_Listexploders_en_zet_attributen_volgens_definitie__in_onderzoek_en_plus-status__36
Deaggregator_2
    SPLIT_COMPOSITES = No
    GEOM_NAME_FIELD = _geometry_name
    EXPLODE_INSTANCES = No
    MODE = Flatten One Level
    PART_NUMBER_FIELD = _part_number
    LIST_ATTR_MODE_LOOKUP = LEAN
    DEAGGREGATED -> GeometryFilter_onbegroeidTerreindeel
GeometryFilter_onbegroeidTerreindeel
    GEOM_PORT_NAMES = Line Area
    BREAK_AGG = No
    LINE -> Verwijder_overbodige_attributen_37
    AREA -> Verwijder_overbodige_attributen_35
AttributeManager_6
    ATTR_TABLE:
      REMOVE _element_index
      REMOVE fme_rejection_code
      SET_TO horend_bij = onbegroeid terreindeel
    -> Verwijder_attributen_uit_Listexploders_en_zet_attributen_volgens_definitie__in_onderzoek_en_plus-status__36

Bookmark: Input
Bak (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, imgeo_plus-type xml_buffer, imgeo_plus-type_codeSpace xml_buffer
    -> Verwijder_overbodige_attributen_17
Bord (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, imgeo_plus-type xml_buffer, imgeo_plus-type_codeSpace xml_buffer
    -> Verwijder_overbodige_attributen_18
BridgeConstructionElement (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, citygml_bounded_by{}.xlink_href xml_buffer, citygml___generic_application_property_of_bridge_construction_element{} xml_xml, imgeo_hoort_bij_type_overbrugging{} xml_buffer, imgeo_hoort_bij_type_overbrugging{}.codeSpace xml_buffer, imgeo_overbrugging_is_beweegbaar{} xml_boolean
    -> Verwijder_overbodige_attributen_19
BuildingInstallation (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, citygml_bounded_by{}.xlink_href xml_buffer, imgeo_plus-type_gebouw_installatie{} xml_buffer, imgeo_plus-type_gebouw_installatie{}.codeSpace xml_buffer
    -> Verwijder_overbodige_attributen_20
FunctioneelGebied (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, imgeo_bgt-type xml_buffer, imgeo_bgt-type_codeSpace xml_buffer, imgeo_plus-type xml_buffer, imgeo_plus-type_codeSpace xml_buffer, imgeo_naam xml_buffer, imgeo_naam_codeSpace xml_buffer
    -> Verwijder_overbodige_attributen_21
Installatie (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, imgeo_plus-type xml_buffer, imgeo_plus-type_codeSpace xml_buffer
    -> Verwijder_overbodige_attributen_22
Kast (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, imgeo_plus-type xml_buffer, imgeo_plus-type_codeSpace xml_buffer
    -> Verwijder_overbodige_attributen_23
Kunstwerkdeel (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_level_of_detail{} xml_buffer, imgeo_bgt-type xml_buffer, imgeo_bgt-type_codeSpace xml_buffer, imgeo_plus-type xml_buffer,
      imgeo_plus-type_codeSpace xml_buffer
    -> Verwijder_overbodige_attributen_24
Mast (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, imgeo_plus-type xml_buffer, imgeo_plus-type_codeSpace xml_buffer
    -> Verwijder_overbodige_attributen_25
OndersteunendWaterdeel (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, citygml_bounded_by{}.xlink_href xml_buffer, imgeo_plus-type xml_buffer, imgeo_plus-type_codeSpace xml_buffer
    -> Verwijder_overbodige_attributen_27
OngeclassificeerdObject (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime
    -> Verwijder_overbodige_attributen_28
OpenbareRuimteLabel (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, imgeo_identificatie_bagopr xml_buffer, imgeo_openbare_ruimte_naam xml_xml, imgeo_openbare_ruimte_type xml_buffer, imgeo_openbare_ruimte_type_codeSpace xml_buffer
    -> OpenbareRuimteLabelExtractor
OverigBouwwerk (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_level_of_detail{} xml_buffer, imgeo_bgt-type xml_buffer, imgeo_bgt-type_codeSpace xml_buffer, imgeo_plus-type xml_buffer,
      imgeo_plus-type_codeSpace xml_buffer
    -> Verwijder_overbodige_attributen_30
OverigeScheiding (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_level_of_detail{} xml_buffer, imgeo_plus-type xml_buffer, imgeo_plus-type_codeSpace xml_buffer
    -> Verwijder_overbodige_attributen_9
BuildingPart (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, imgeo_identificatie_bagpnd{} xml_buffer, imgeo_nummeraanduidingreeks{}.imgeo_nummeraanduidingreeks_imgeo_nummeraanduidingreeks xml_xml, imgeo_nummeraanduidingreeks{}.imgeo_nummeraanduidingreeks_imgeo_identificatie_bagvbolaagste_huisnummer xml_buffer, imgeo_nummeraanduidingreeks{}.imgeo_nummeraanduidingreeks_imgeo_identificatie_bagvbohoogste_huisnummer xml_buffer
    -> Verwijder_overbodige_attributen
    -> Verwijder_overbodige_attributen_32
Paal (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, imgeo_hectometeraanduiding xml_buffer, imgeo_plus-type xml_buffer, imgeo_plus-type_codeSpace xml_buffer
    -> Verwijder_overbodige_attributen_2
Plaatsbepalingspunt (reader CITYGML_1) [off]
    attributes: citygml_target_uri xml_buffer, citygml_feature_role xml_buffer, citygml_feature_role_attr_name xml_buffer, citygml_feature_role_attr_val xml_buffer, gml_description xml_buffer, gml_name xml_buffer, imgeo_identificatie_imgeo_nen3610_id_imgeo_namespace xml_buffer, imgeo_identificatie_imgeo_nen3610_id_imgeo_lokaal_id xml_buffer, imgeo_nauwkeurigheid xml_int64, imgeo_nauwkeurigheid_nilReason xml_buffer, imgeo_nauwkeurigheid_xsi_nil xml_boolean, imgeo_datum_inwinning xml_date, imgeo_inwinnende_instantie xml_buffer, imgeo_inwinnende_instantie_nilReason xml_buffer, imgeo_inwinnende_instantie_xsi_nil xml_boolean, imgeo_inwinningsmethode xml_buffer, imgeo_inwinningsmethode_codeSpace xml_buffer
    -> Verwijder_overbodige_attributen_10
Put (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, imgeo_plus-type xml_buffer, imgeo_plus-type_codeSpace xml_buffer
    -> Verwijder_overbodige_attributen_3
Scheiding (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_level_of_detail{} xml_buffer, imgeo_bgt-type xml_buffer, imgeo_bgt-type_codeSpace xml_buffer, imgeo_plus-type xml_buffer,
      imgeo_plus-type_codeSpace xml_buffer
    -> Verwijder_overbodige_attributen_4
Sensor (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, imgeo_plus-type xml_buffer, imgeo_plus-type_codeSpace xml_buffer
    -> Verwijder_overbodige_attributen_11
Railway (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_traffic_area{}.xlink_href xml_buffer, citygml_auxiliary_traffic_area{}.xlink_href xml_buffer, citygml_level_of_detail{} xml_buffer, imgeo_plus-functie_spoor{} xml_buffer, imgeo_plus-functie_spoor{}.codeSpace xml_buffer
    -> Verwijder_overbodige_attributen_5
Straatmeubilair (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, imgeo_plus-type xml_buffer, imgeo_plus-type_codeSpace xml_buffer
    -> Verwijder_overbodige_attributen_6
TunnelPart (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_year_of_construction xml_buffer, citygml_year_of_demolition xml_buffer, citygml_outer_tunnel_installation{}.xlink_href xml_buffer, citygml_interior_tunnel_installation{}.xlink_href xml_buffer, citygml_bounded_by{}.xlink_href xml_buffer, citygml_level_of_detail{} xml_buffer, citygml_interior_hollow_space{}.xlink_href xml_buffer, citygml_consists_of_tunnel_part{}.xlink_href xml_buffer
    -> Verwijder_overbodige_attributen_12
SolitaryVegetationObject (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_species xml_buffer, citygml_species_codeSpace xml_buffer, citygml_height xml_real64, citygml_height_units xml_buffer, citygml_trunk_diameter xml_real64, citygml_trunk_diameter_units xml_buffer, citygml_crown_diameter xml_real64, citygml_crown_diameter_units xml_buffer, citygml_level_of_detail{} xml_buffer, imgeo_plus-type{} xml_buffer, imgeo_plus-type{}.codeSpace xml_buffer
    -> Verwijder_overbodige_attributen_7
Waterdeel (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, citygml_bounded_by{}.xlink_href xml_buffer, imgeo_plus-type xml_buffer, imgeo_plus-type_codeSpace xml_buffer
    -> Verwijder_overbodige_attributen_8
Waterinrichtingselement (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, imgeo_plus-type xml_buffer, imgeo_plus-type_codeSpace xml_buffer
    -> Verwijder_overbodige_attributen_13
Weginrichtingselement (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, imgeo_plus-type xml_buffer, imgeo_plus-type_codeSpace xml_buffer
    -> Verwijder_overbodige_attributen_15
TrafficArea (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_surface_material xml_buffer, citygml_surface_material_codeSpace xml_buffer, citygml_level_of_detail{} xml_buffer, imgeo_plus-fysiek_voorkomen_wegdeel{} xml_buffer, imgeo_plus-fysiek_voorkomen_wegdeel{}.codeSpace xml_buffer, imgeo_wegdeel_op_talud{} xml_boolean, imgeo_wegdeel_op_talud{}.nilReason xml_buffer, imgeo_wegdeel_op_talud{}.xsi_nil xml_boolean, imgeo_plus-functie_wegdeel{} xml_buffer, imgeo_plus-functie_wegdeel{}.codeSpace xml_buffer
    -> Deaggregator_4
AuxiliaryTrafficArea (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_surface_material xml_buffer, citygml_surface_material_codeSpace xml_buffer, citygml_level_of_detail{} xml_buffer, imgeo_ondersteunend_wegdeel_op_talud{} xml_boolean, imgeo_ondersteunend_wegdeel_op_talud{}.nilReason xml_buffer, imgeo_ondersteunend_wegdeel_op_talud{}.xsi_nil xml_boolean, imgeo_plus-functie_ondersteunend_wegdeel{} xml_buffer, imgeo_plus-functie_ondersteunend_wegdeel{}.codeSpace xml_buffer, imgeo_plus-fysiek_voorkomen_ondersteunend_wegdeel{} xml_buffer, imgeo_plus-fysiek_voorkomen_ondersteunend_wegdeel{}.codeSpace xml_buffer
    -> Deaggregator_3
PlantCover (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_average_height xml_real64, citygml_average_height_units xml_buffer, citygml_level_of_detail{} xml_buffer, imgeo_plus-fysiek_voorkomen{} xml_buffer, imgeo_plus-fysiek_voorkomen{}.codeSpace xml_buffer, imgeo_begroeid_terreindeel_op_talud{} xml_boolean, imgeo_begroeid_terreindeel_op_talud{}.nilReason xml_buffer, imgeo_begroeid_terreindeel_op_talud{}.xsi_nil xml_boolean
    -> Deaggregator
OnbegroeidTerreindeel (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), imgeo_bgt-status{} xml_buffer, imgeo_bgt-status{}.codeSpace xml_buffer, imgeo_bronhouder{} xml_buffer, imgeo_tijdstip_registratie{} xml_datetime, imgeo_lv-publicatiedatum{} xml_datetime, imgeo_identificatie{}.imgeo_nen3610_id_imgeo_namespace xml_buffer, imgeo_identificatie{}.imgeo_nen3610_id_imgeo_lokaal_id xml_buffer, imgeo_in_onderzoek{} xml_boolean, imgeo_relatieve_hoogteligging{} xml_int64, imgeo_plus-status{} xml_buffer, imgeo_plus-status{}.codeSpace xml_buffer, imgeo_eind_registratie{} xml_datetime, citygml_class xml_buffer, citygml_class_codeSpace xml_buffer, citygml_function{} xml_buffer, citygml_function{}.codeSpace xml_buffer,
      citygml_usage{} xml_buffer, citygml_usage{}.codeSpace xml_buffer, citygml_level_of_detail{} xml_buffer, imgeo_bgt-fysiek_voorkomen xml_buffer, imgeo_bgt-fysiek_voorkomen_codeSpace xml_buffer, imgeo_onbegroeid_terreindeel_op_talud xml_boolean, imgeo_onbegroeid_terreindeel_op_talud_nilReason xml_buffer, imgeo_onbegroeid_terreindeel_op_talud_xsi_nil xml_boolean, imgeo_plus-fysiek_voorkomen xml_buffer, imgeo_plus-fysiek_voorkomen_codeSpace xml_buffer
    -> Deaggregator_2

Bookmark: Rename - en Verwijder input-attributen
Note: Verwijder_overbodige_attributen
Verwijder_overbodige_attributen_17: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > bgt_type = niet-bgt
      REMOVE citygml_class_codeSpace
      REMOVE citygml_function{}
      REMOVE citygml_function{}.codeSpace
      REMOVE citygml_usage{}
      REMOVE citygml_usage{}.codeSpace
      RENAME_SET_VALUE imgeo_plus-type > plus_type
      REMOVE imgeo_plus-type_codeSpace
    -> Generieke_attributen_16
Note: Verwijder_overbodige_attributen
Verwijder_overbodige_attributen_18: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > bgt_type = niet-bgt
      REMOVE citygml_class_codeSpace
      REMOVE citygml_function{}
      REMOVE citygml_function{}.codeSpace
      REMOVE citygml_usage{}
      REMOVE citygml_usage{}.codeSpace
      RENAME_SET_VALUE imgeo_plus-type > plus_type
      REMOVE imgeo_plus-type_codeSpace
    -> Generieke_attributen_17
Note: Verwijder_overbodige_attributen
Verwijder_overbodige_attributen_19: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > plus_type
      REMOVE citygml_class_codeSpace
      REMOVE citygml_function{}
      REMOVE citygml_function{}.codeSpace
      REMOVE citygml_usage{}
      REMOVE citygml_usage{}.codeSpace
      REMOVE citygml_bounded_by{}.xlink_href
      REMOVE citygml___generic_application_property_of_bridge_construction_element{}
      RENAME_SET_VALUE imgeo_hoort_bij_type_overbrugging{} > hoortbijtypeoverbrugging{}
      REMOVE imgeo_hoort_bij_type_overbrugging{}.codeSpace
      RENAME_SET_VALUE imgeo_overbrugging_is_beweegbaar{} > overbruggingisbeweegbaar{}
    -> Generieke_attributen_18
Note: Verwijder_overbodige_attributen
Verwijder_overbodige_attributen_20: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > bgt_type = niet-bgt
      REMOVE citygml_class_codeSpace
      REMOVE citygml_function{}
      REMOVE citygml_function{}.codeSpace
      REMOVE citygml_usage{}
      REMOVE citygml_usage{}.codeSpace
      REMOVE citygml_bounded_by{}.xlink_href
      RENAME_SET_VALUE imgeo_plus-type_gebouw_installatie{} > plus_type{}
      REMOVE imgeo_plus-type_gebouw_installatie{}.codeSpace
    -> Generieke_attributen_19
Note: Verwijder_overbodige_attributen
Verwijder_overbodige_attributen_21: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      REMOVE citygml_class
      REMOVE citygml_class_codeSpace
      REMOVE citygml_function{}
      REMOVE citygml_function{}.codeSpace
      REMOVE citygml_usage{}
      REMOVE citygml_usage{}.codeSpace
      RENAME_SET_VALUE imgeo_bgt-type > bgt_type
      REMOVE imgeo_bgt-type_codeSpace
      RENAME_SET_VALUE imgeo_plus-type > plus_type
      REMOVE imgeo_plus-type_codeSpace
      RENAME_SET_VALUE imgeo_naam > naam
      REMOVE imgeo_naam_codeSpace
    -> Generieke_attributen_20
Note: Verwijder_overbodige_attributen
Verwijder_overbodige_attributen_22: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > bgt_type = niet-bgt
      REMOVE citygml_class_codeSpace
      REMOVE citygml_function{}
      REMOVE citygml_function{}.codeSpace
      REMOVE citygml_usage{}
      REMOVE citygml_usage{}.codeSpace
      RENAME_SET_VALUE imgeo_plus-type > plus_type
      REMOVE imgeo_plus-type_codeSpace
    -> Generieke_attributen_21
Note: Verwijder_overbodige_attributen
Verwijder_overbodige_attributen_23: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > bgt_type = niet-bgt
      REMOVE citygml_class_codeSpace
      REMOVE citygml_function{}
      REMOVE citygml_function{}.codeSpace
      REMOVE citygml_usage{}
      REMOVE citygml_usage{}.codeSpace
      RENAME_SET_VALUE imgeo_plus-type > plus_type
      REMOVE imgeo_plus-type_codeSpace
    -> Generieke_attributen_22
Note: Verwijder_overbodige_attributen
Verwijder_overbodige_attributen_24: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE imgeo_bgt-type > bgt_type
      REMOVE imgeo_bgt-type_codeSpace
      RENAME_SET_VALUE imgeo_plus-type > plus_type
      REMOVE imgeo_plus-type_codeSpace
    -> Generieke_attributen_23
Note: Verwijder_overbodige_attributen
Verwijder_overbodige_attributen_25: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > bgt_type = niet-bgt
      REMOVE citygml_class_codeSpace
      REMOVE citygml_function{}
      REMOVE citygml_function{}.codeSpace
      REMOVE citygml_usage{}
      REMOVE citygml_usage{}.codeSpace
      RENAME_SET_VALUE imgeo_plus-type > plus_type
      REMOVE imgeo_plus-type_codeSpace
    -> Generieke_attributen_24
Note: Verwijder_overbodige_attributen
Verwijder_overbodige_attributen_27: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > bgt_type
      REMOVE citygml_class_codeSpace
      REMOVE citygml_function{}
      REMOVE citygml_function{}.codeSpace
      REMOVE citygml_usage{}
      REMOVE citygml_usage{}.codeSpace
      REMOVE citygml_bounded_by{}.xlink_href
      RENAME_SET_VALUE imgeo_plus-type > plus_type
      REMOVE imgeo_plus-type_codeSpace
    -> Generieke_attributen_26
Note: Verwijder_overbodige_attributen
Verwijder_overbodige_attributen_28: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE gml_id
      REMOVE gml_parent_id
    -> Generieke_attributen_27
Note: Verwijder_overbodige_attributen
Verwijder_overbodige_attributen_33: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE gml_id
      REMOVE gml_parent_id
      RENAME_SET_VALUE imgeo_identificatie_bagopr > identificatieBAGOPR
      RENAME_SET_VALUE imgeo_openbare_ruimte_naam > label_tekst
      RENAME_SET_VALUE imgeo_openbare_ruimte_type > openbareruimte_type
      REMOVE imgeo_openbare_ruimte_type_codeSpace
      REMOVE _xq_compound_positie
      REMOVE _source_compound_positie
    -> Generieke_attributen_28
Note: Verwijder_overbodige_attributen
Verwijder_overbodige_attributen_30: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE imgeo_bgt-type > bgt_type
      REMOVE imgeo_bgt-type_codeSpace
      RENAME_SET_VALUE imgeo_plus-type > plus_type
      REMOVE imgeo_plus-type_codeSpace
    -> Generieke_attributen_29
Verwijder_overbodige_attributen_9: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE imgeo_plus-type > plus_type
      REMOVE imgeo_plus-type_codeSpace
      SET_TO bgt_type = niet-bgt
    -> Generieke_attributen_9
Note: Verwijder_overbodige_attributen
Verwijder_overbodige_attributen_32: AttributeManager
    ATTR_TABLE:
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      RENAME_SET_VALUE imgeo_identificatie_bagpnd{} > identificatiebagpnd{}
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_class
      REMOVE citygml_class_codeSpace
      REMOVE citygml_function{}
      REMOVE citygml_function{}.codeSpace
      REMOVE citygml_usage{}
      REMOVE citygml_usage{}.codeSpace
      REMOVE citygml_year_of_construction
      REMOVE citygml_year_of_demolition
      REMOVE citygml_roof_type
      REMOVE citygml_roof_type_codeSpace
      REMOVE citygml_measured_height
      REMOVE citygml_measured_height_units
      REMOVE citygml_storeys_above_ground
      REMOVE citygml_storeys_below_ground
      REMOVE citygml_storey_heights_above_ground
      REMOVE citygml_storey_heights_above_ground_units
      REMOVE citygml_storey_heights_below_ground
      REMOVE citygml_storey_heights_below_ground_units
      REMOVE citygml_outer_building_installation{}.xlink_href
      REMOVE citygml_interior_building_installation{}.xlink_href
      REMOVE citygml_bounded_by{}.xlink_href
      REMOVE citygml_level_of_detail{}
      REMOVE citygml_interior_room{}.xlink_href
      REMOVE citygml_consists_of_building_part{}.xlink_href
      REMOVE citygml_address{}.xlink_href
      REMOVE gml_parent_id
    -> ListExploder
Note: Verwijder_overbodige_attributen
Verwijder_overbodige_attributen: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      RENAME_SET_VALUE imgeo_identificatie_bagpnd{} > identificatiebagpnd{}
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_class
      REMOVE citygml_class_codeSpace
      REMOVE citygml_function{}
      REMOVE citygml_function{}.codeSpace
      REMOVE citygml_usage{}
      REMOVE citygml_usage{}.codeSpace
      REMOVE citygml_year_of_construction
      REMOVE citygml_year_of_demolition
      REMOVE citygml_roof_type
      REMOVE citygml_roof_type_codeSpace
      REMOVE citygml_measured_height
      REMOVE citygml_measured_height_units
      REMOVE citygml_storeys_above_ground
      REMOVE citygml_storeys_below_ground
      REMOVE citygml_storey_heights_above_ground
      REMOVE citygml_storey_heights_above_ground_units
      REMOVE citygml_storey_heights_below_ground
      REMOVE citygml_storey_heights_below_ground_units
      REMOVE citygml_outer_building_installation{}.xlink_href
      REMOVE citygml_interior_building_installation{}.xlink_href
      REMOVE citygml_bounded_by{}.xlink_href
      REMOVE citygml_level_of_detail{}
      REMOVE citygml_interior_room{}.xlink_href
      REMOVE citygml_consists_of_building_part{}.xlink_href
      REMOVE citygml_address{}.xlink_href
      REMOVE imgeo_nummeraanduidingreeks{}.imgeo_nummeraanduidingreeks_imgeo_nummeraanduidingreeks
      REMOVE imgeo_nummeraanduidingreeks{}.imgeo_nummeraanduidingreeks_imgeo_identificatie_bagvbolaagste_huisnummer
      REMOVE imgeo_nummeraanduidingreeks{}.imgeo_nummeraanduidingreeks_imgeo_identificatie_bagvbohoogste_huisnummer
      REMOVE gml_id
      REMOVE gml_parent_id
    -> Generieke_attributen
Note: Verwijder_overbodige_attributen
Verwijder_overbodige_attributen_2: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      RENAME_SET_VALUE citygml_class > bgt_type = niet-bgt
      REMOVE citygml_class_codeSpace
      REMOVE citygml_function{}
      REMOVE citygml_function{}.codeSpace
      REMOVE citygml_usage{}
      REMOVE citygml_usage{}.codeSpace
      REMOVE citygml_level_of_detail{}
      REMOVE gml_id
      REMOVE gml_parent_id
      RENAME_SET_VALUE imgeo_hectometeraanduiding > hectometeraanduiding
      RENAME_SET_VALUE imgeo_plus-type > plus_type
      REMOVE imgeo_plus-type_codeSpace
    -> Generieke_attributen_2
Note: Verwijder_overbodige_attributen
Verwijder_overbodige_attributen_10: AttributeManager
    ATTR_TABLE:
      REMOVE gml_name
      REMOVE citygml_target_uri
      REMOVE citygml_feature_role
      REMOVE citygml_feature_role_attr_name
      REMOVE citygml_feature_role_attr_val
      REMOVE gml_description
      REMOVE gml_id
      REMOVE gml_parent_id
      RENAME_SET_VALUE imgeo_identificatie_imgeo_nen3610_id_imgeo_namespace > nen3610_id_imgeo_namespace
      RENAME_SET_VALUE imgeo_identificatie_imgeo_nen3610_id_imgeo_lokaal_id > nen3610_id_imgeo_lokaal_id
      RENAME_SET_VALUE imgeo_nauwkeurigheid > nauwkeurigheid
      REMOVE imgeo_nauwkeurigheid_nilReason
      REMOVE imgeo_nauwkeurigheid_xsi_nil
      RENAME_SET_VALUE imgeo_datum_inwinning > datuminwinning
      RENAME_SET_VALUE imgeo_inwinnende_instantie > inwinnendeinstantie
      REMOVE imgeo_inwinnende_instantie_nilReason
      REMOVE imgeo_inwinnende_instantie_xsi_nil
      RENAME_SET_VALUE imgeo_inwinningsmethode > inwinningsmethode
      REMOVE imgeo_inwinningsmethode_codeSpace
    -> imgeo.bgt_plaatsbepalingspunt (writer POSTGIS_1)
Note: Verwijder_overbodige_attributen
Verwijder_overbodige_attributen_3: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      RENAME_SET_VALUE citygml_class > bgt_type = niet-bgt
      REMOVE citygml_class_codeSpace
      REMOVE citygml_function{}
      REMOVE citygml_function{}.codeSpace
      REMOVE citygml_usage{}
      REMOVE citygml_usage{}.codeSpace
      REMOVE citygml_level_of_detail{}
      REMOVE gml_id
      REMOVE gml_parent_id
      RENAME_SET_VALUE imgeo_plus-type > plus_type
      REMOVE imgeo_plus-type_codeSpace
    -> Generieke_attributen_3
Note: Verwijder_overbodige_attributen
Verwijder_overbodige_attributen_4: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE imgeo_plus-type > plus_type
      REMOVE imgeo_plus-type_codeSpace
      RENAME_SET_VALUE imgeo_bgt-type > bgt_type
      REMOVE imgeo_bgt-type_codeSpace
    -> Generieke_attributen_4
Note: Verwijder_overbodige_attributen
Verwijder_overbodige_attributen_11: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      RENAME_SET_VALUE citygml_class > bgt_type = niet-bgt
      REMOVE citygml_class_codeSpace
      REMOVE citygml_function{}
      REMOVE citygml_function{}.codeSpace
      REMOVE citygml_usage{}
      REMOVE citygml_usage{}.codeSpace
      REMOVE citygml_level_of_detail{}
      REMOVE gml_id
      REMOVE gml_parent_id
      RENAME_SET_VALUE imgeo_plus-type > plus_type
      REMOVE imgeo_plus-type_codeSpace
    -> Generieke_attributen_10
Note: Verwijder_overbodige_attributen
Verwijder_overbodige_attributen_5: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      REMOVE citygml_class
      REMOVE citygml_class_codeSpace
      RENAME_SET_VALUE citygml_function{} > bgt_functie{}
      REMOVE citygml_function{}.codeSpace
      REMOVE citygml_usage{}
      REMOVE citygml_usage{}.codeSpace
      REMOVE citygml_traffic_area{}.xlink_href
      REMOVE citygml_auxiliary_traffic_area{}.xlink_href
      RENAME_SET_VALUE imgeo_plus-functie_spoor{} > plus_functie{}
      REMOVE imgeo_plus-functie_spoor{}.codeSpace
    -> Generieke_attributen_5
Note: Verwijder_overbodige_attributen
Verwijder_overbodige_attributen_6: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > bgt_type = niet-bgt
      REMOVE citygml_class_codeSpace
      REMOVE citygml_function{}
      REMOVE citygml_function{}.codeSpace
      REMOVE citygml_usage{}
      REMOVE citygml_usage{}.codeSpace
      RENAME_SET_VALUE imgeo_plus-type > plus_type
      REMOVE imgeo_plus-type_codeSpace
    -> Generieke_attributen_6
Note: Verwijder_overbodige_attributen
Verwijder_overbodige_attributen_12: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      REMOVE citygml_class
      REMOVE citygml_class_codeSpace
      REMOVE citygml_function{}
      REMOVE citygml_function{}.codeSpace
      REMOVE citygml_usage{}
      REMOVE citygml_usage{}.codeSpace
      REMOVE citygml_bounded_by{}.xlink_href
      REMOVE citygml_year_of_construction
      REMOVE citygml_year_of_demolition
      REMOVE citygml_outer_tunnel_installation{}.xlink_href
      REMOVE citygml_interior_tunnel_installation{}.xlink_href
      REMOVE citygml_interior_hollow_space{}.xlink_href
      REMOVE citygml_consists_of_tunnel_part{}.xlink_href
    -> Generieke_attributen_11
Note: Verwijder_overbodige_attributen
Verwijder_overbodige_attributen_7: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > bgt_type = niet-bgt
      REMOVE citygml_class_codeSpace
      REMOVE citygml_function{}
      REMOVE citygml_function{}.codeSpace
      REMOVE citygml_usage{}
      REMOVE citygml_usage{}.codeSpace
      REMOVE citygml_species
      REMOVE citygml_species_codeSpace
      REMOVE citygml_height
      REMOVE citygml_height_units
      REMOVE citygml_trunk_diameter
      REMOVE citygml_trunk_diameter_units
      REMOVE citygml_crown_diameter
      REMOVE citygml_crown_diameter_units
      RENAME_SET_VALUE imgeo_plus-type{} > plus_type{}
      REMOVE imgeo_plus-type{}.codeSpace
    -> Generieke_attributen_7
Note: Verwijder_overbodige_attributen
Verwijder_overbodige_attributen_8: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > bgt_type
      REMOVE citygml_class_codeSpace
      REMOVE citygml_function{}
      REMOVE citygml_function{}.codeSpace
      REMOVE citygml_usage{}
      REMOVE citygml_usage{}.codeSpace
      REMOVE citygml_bounded_by{}.xlink_href
      RENAME_SET_VALUE imgeo_plus-type > plus_type
      REMOVE imgeo_plus-type_codeSpace
    -> Generieke_attributen_8
Note: Verwijder_overbodige_attributen
Verwijder_overbodige_attributen_13: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > bgt_type = niet-bgt
      REMOVE citygml_class_codeSpace
      REMOVE citygml_function{}
      REMOVE citygml_function{}.codeSpace
      REMOVE citygml_usage{}
      REMOVE citygml_usage{}.codeSpace
      RENAME_SET_VALUE imgeo_plus-type > plus_type
      REMOVE imgeo_plus-type_codeSpace
    -> Generieke_attributen_12
Note: Verwijder_overbodige_attributen
Verwijder_overbodige_attributen_15: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > bgt_type = niet-bgt
      REMOVE citygml_class_codeSpace
      REMOVE citygml_function{}
      REMOVE citygml_function{}.codeSpace
      REMOVE citygml_usage{}
      REMOVE citygml_usage{}.codeSpace
      RENAME_SET_VALUE imgeo_plus-type > plus_type
      REMOVE imgeo_plus-type_codeSpace
    -> Generieke_attributen_14
Note: Verwijder_overbodige_attributen
Verwijder_overbodige_attributen_39: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      REMOVE citygml_class
      REMOVE citygml_class_codeSpace
      REMOVE citygml_function{}
      REMOVE citygml_function{}.codeSpace
      REMOVE citygml_usage{}
      REMOVE citygml_usage{}.codeSpace
      REMOVE citygml_surface_material
      REMOVE citygml_surface_material_codeSpace
      REMOVE imgeo_plus-fysiek_voorkomen_wegdeel{}
      REMOVE imgeo_plus-fysiek_voorkomen_wegdeel{}.codeSpace
      RENAME_SET_VALUE imgeo_wegdeel_op_talud{} > optalud{}
      REMOVE imgeo_wegdeel_op_talud{}.nilReason
      REMOVE imgeo_wegdeel_op_talud{}.xsi_nil
      REMOVE imgeo_plus-functie_wegdeel{}
      REMOVE imgeo_plus-functie_wegdeel{}.codeSpace
      REMOVE fme_geometry
      REMOVE _geometry_name
      REMOVE _part_number
    -> Generieke_attributen_39
Note: Verwijder_overbodige_attributen
Verwijder_overbodige_attributen_29: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      REMOVE citygml_class
      REMOVE citygml_class_codeSpace
      RENAME_SET_VALUE citygml_function{} > bgt_functie{}
      REMOVE citygml_function{}.codeSpace
      REMOVE citygml_usage{}
      REMOVE citygml_usage{}.codeSpace
      RENAME_SET_VALUE citygml_surface_material > bgt_fysiekvoorkomen
      REMOVE citygml_surface_material_codeSpace
      RENAME_SET_VALUE imgeo_plus-fysiek_voorkomen_wegdeel{} > plus_fysiekvoorkomen{}
      REMOVE imgeo_plus-fysiek_voorkomen_wegdeel{}.codeSpace
      RENAME_SET_VALUE imgeo_wegdeel_op_talud{} > optalud{}
      REMOVE imgeo_wegdeel_op_talud{}.nilReason
      REMOVE imgeo_wegdeel_op_talud{}.xsi_nil
      RENAME_SET_VALUE imgeo_plus-functie_wegdeel{} > plus_functie{}
      REMOVE imgeo_plus-functie_wegdeel{}.codeSpace
      REMOVE fme_geometry
      REMOVE _geometry_name
      REMOVE _part_number
    -> Generieke_attributen_32
Note: Verwijder_overbodige_attributen
Verwijder_overbodige_attributen_38: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      REMOVE citygml_class
      REMOVE citygml_class_codeSpace
      REMOVE citygml_function{}
      REMOVE citygml_function{}.codeSpace
      REMOVE citygml_usage{}
      REMOVE citygml_usage{}.codeSpace
      REMOVE citygml_surface_material
      REMOVE citygml_surface_material_codeSpace
      RENAME_SET_VALUE imgeo_ondersteunend_wegdeel_op_talud{} > optalud{}
      REMOVE imgeo_ondersteunend_wegdeel_op_talud{}.nilReason
      REMOVE imgeo_ondersteunend_wegdeel_op_talud{}.xsi_nil
      REMOVE imgeo_plus-functie_ondersteunend_wegdeel{}
      REMOVE imgeo_plus-functie_ondersteunend_wegdeel{}.codeSpace
      REMOVE imgeo_plus-fysiek_voorkomen_ondersteunend_wegdeel{}
      REMOVE imgeo_plus-fysiek_voorkomen_ondersteunend_wegdeel{}.codeSpace
      REMOVE fme_geometry
      REMOVE _geometry_name
      REMOVE _part_number
    -> Generieke_attributen_38
Note: Verwijder_overbodige_attributen
Verwijder_overbodige_attributen_34: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      REMOVE citygml_class
      REMOVE citygml_class_codeSpace
      RENAME_SET_VALUE citygml_function{} > bgt_functie{}
      REMOVE citygml_function{}.codeSpace
      REMOVE citygml_usage{}
      REMOVE citygml_usage{}.codeSpace
      RENAME_SET_VALUE citygml_surface_material > bgt_fysiekvoorkomen
      REMOVE citygml_surface_material_codeSpace
      RENAME_SET_VALUE imgeo_ondersteunend_wegdeel_op_talud{} > optalud{}
      REMOVE imgeo_ondersteunend_wegdeel_op_talud{}.nilReason
      REMOVE imgeo_ondersteunend_wegdeel_op_talud{}.xsi_nil
      RENAME_SET_VALUE imgeo_plus-functie_ondersteunend_wegdeel{} > plus_functie{}
      REMOVE imgeo_plus-functie_ondersteunend_wegdeel{}.codeSpace
      RENAME_SET_VALUE imgeo_plus-fysiek_voorkomen_ondersteunend_wegdeel{} > plus_fysiekvoorkomen{}
      REMOVE imgeo_plus-fysiek_voorkomen_ondersteunend_wegdeel{}.codeSpace
      REMOVE fme_geometry
      REMOVE _geometry_name
      REMOVE _part_number
    -> Generieke_attributen_33
Note: Verwijder_overbodige_attributen_kruinlijn
Verwijder_overbodige_attributen_kruinlijn: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      REMOVE citygml_class
      REMOVE citygml_class_codeSpace
      REMOVE citygml_function{}
      REMOVE citygml_function{}.codeSpace
      REMOVE citygml_usage{}
      REMOVE citygml_usage{}.codeSpace
      REMOVE citygml_average_height
      REMOVE citygml_average_height_units
      REMOVE imgeo_plus-fysiek_voorkomen{}
      REMOVE imgeo_plus-fysiek_voorkomen{}.codeSpace
      RENAME_SET_VALUE imgeo_begroeid_terreindeel_op_talud{} > optalud{}
      REMOVE imgeo_begroeid_terreindeel_op_talud{}.nilReason
      REMOVE imgeo_begroeid_terreindeel_op_talud{}.xsi_nil
      REMOVE fme_geometry
      REMOVE _geometry_name
      REMOVE _part_number
    -> Generieke_attributen_36
Note: Verwijder_overbodige_attributen
Verwijder_overbodige_attributen_36: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      RENAME_SET_VALUE citygml_class > bgt_fysiekvoorkomen
      REMOVE citygml_class_codeSpace
      REMOVE citygml_function{}
      REMOVE citygml_function{}.codeSpace
      REMOVE citygml_usage{}
      REMOVE citygml_usage{}.codeSpace
      REMOVE citygml_average_height
      REMOVE citygml_average_height_units
      RENAME_SET_VALUE imgeo_plus-fysiek_voorkomen{} > plus_fysiekvoorkomen{}
      REMOVE imgeo_plus-fysiek_voorkomen{}.codeSpace
      RENAME_SET_VALUE imgeo_begroeid_terreindeel_op_talud{} > optalud{}
      REMOVE imgeo_begroeid_terreindeel_op_talud{}.nilReason
      REMOVE imgeo_begroeid_terreindeel_op_talud{}.xsi_nil
      REMOVE fme_geometry
      REMOVE _geometry_name
      REMOVE _part_number
    -> Generieke_attributen_35
Note: Verwijder_overbodige_attributen
Verwijder_overbodige_attributen_37: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      REMOVE citygml_class
      REMOVE citygml_class_codeSpace
      REMOVE citygml_function{}
      REMOVE citygml_function{}.codeSpace
      REMOVE citygml_usage{}
      REMOVE citygml_usage{}.codeSpace
      REMOVE imgeo_bgt-fysiek_voorkomen
      REMOVE imgeo_bgt-fysiek_voorkomen_codeSpace
      RENAME_SET_VALUE imgeo_onbegroeid_terreindeel_op_talud > optalud
      REMOVE imgeo_onbegroeid_terreindeel_op_talud_nilReason
      REMOVE imgeo_onbegroeid_terreindeel_op_talud_xsi_nil
      REMOVE imgeo_plus-fysiek_voorkomen
      REMOVE imgeo_plus-fysiek_voorkomen_codeSpace
      REMOVE fme_geometry
      REMOVE _geometry_name
      REMOVE _part_number
    -> Generieke_attributen_37
Note: Verwijder_overbodige_attributen
Verwijder_overbodige_attributen_35: AttributeManager
    ATTR_TABLE:
      RENAME_SET_VALUE imgeo_identificatie{}.imgeo_nen3610_id_imgeo_namespace > imgeo_identificatie{}.identificatie_namespace
      RENAME_SET_VALUE imgeo_identificatie{}.imgeo_nen3610_id_imgeo_lokaal_id > imgeo_identificatie{}.identificatie_lokaal_id
      RENAME_SET_VALUE citygml_creationDate > objectbegintijd
      RENAME_SET_VALUE citygml_terminationDate > objecteindtijd
      RENAME_SET_VALUE imgeo_tijdstip_registratie{} > tijdstipregistratie{}
      RENAME_SET_VALUE imgeo_eind_registratie{} > eindregistratie{}
      RENAME_SET_VALUE imgeo_lv-publicatiedatum{} > lv_publicatiedatum{}
      RENAME_SET_VALUE imgeo_bronhouder{} > bronhouder{}
      RENAME_SET_VALUE imgeo_in_onderzoek{} > inonderzoek{}
      RENAME_SET_VALUE imgeo_relatieve_hoogteligging{} > relatievehoogteligging{}
      RENAME_SET_VALUE imgeo_bgt-status{} > bgt_status{}
      REMOVE imgeo_bgt-status{}.codeSpace
      RENAME_SET_VALUE imgeo_plus-status{} > plus_status{}
      REMOVE imgeo_plus-status{}.codeSpace
      REMOVE gml_name
      REMOVE externalReference{}.externalObject.name
      REMOVE citygml_target_uri
      REMOVE citygml_feature_role
      REMOVE citygml_feature_role_attr_name
      REMOVE citygml_feature_role_attr_val
      REMOVE gml_description
      REMOVE externalReference{}.externalObject.uri
      REMOVE externalReference{}.informationSystem
      REMOVE citygml_generalizes_to{}.xlink_href
      REMOVE citygml_relative_to_terrain
      REMOVE citygml_relative_to_water
      REMOVE citygml_level_of_detail{}
      REMOVE gml_id
      REMOVE gml_parent_id
      REMOVE citygml_class
      REMOVE citygml_class_codeSpace
      REMOVE citygml_function{}
      REMOVE citygml_function{}.codeSpace
      REMOVE citygml_usage{}
      REMOVE citygml_usage{}.codeSpace
      RENAME_SET_VALUE imgeo_bgt-fysiek_voorkomen > bgt_fysiekvoorkomen
      REMOVE imgeo_bgt-fysiek_voorkomen_codeSpace
      RENAME_SET_VALUE imgeo_onbegroeid_terreindeel_op_talud > optalud
      REMOVE imgeo_onbegroeid_terreindeel_op_talud_nilReason
      REMOVE imgeo_onbegroeid_terreindeel_op_talud_xsi_nil
      RENAME_SET_VALUE imgeo_plus-fysiek_voorkomen > plus_fysiekvoorkomen
      REMOVE imgeo_plus-fysiek_voorkomen_codeSpace
    -> Generieke_attributen_34

Bookmark: AlleOnterechte Generieke Lists exploderen
Generieke_attributen_16
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_16
Generieke_attributen_17
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_17
Generieke_attributen_18
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_18
Generieke_attributen_19
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_19
Generieke_attributen_20
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_20
Generieke_attributen_21
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_21
Generieke_attributen_22
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_22
Generieke_attributen_23
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_23
Generieke_attributen_24
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_24
Generieke_attributen_26
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_26
Generieke_attributen_27
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_27
Generieke_attributen_28
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_28
Generieke_attributen_29
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_29
Generieke_attributen_9
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_9
Generieke_attributen_31
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_31
Generieke_attributen
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler
Generieke_attributen_2
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_2
Generieke_attributen_3
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_3
Generieke_attributen_4
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_4
Generieke_attributen_10
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_10
Generieke_attributen_5
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_5
Generieke_attributen_6
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_6
Generieke_attributen_11
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_11
Generieke_attributen_7
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_7
Generieke_attributen_8
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_8
Generieke_attributen_12
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_12
Generieke_attributen_14
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_14
Generieke_attributen_39
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_39
Generieke_attributen_32
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_32
Generieke_attributen_38
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_38
Generieke_attributen_33
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_33
Generieke_attributen_36
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_36
Generieke_attributen_35
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_35
Generieke_attributen_37
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_37
Generieke_attributen_34
    LIST_ATTR = eindregistratie{}
    LIST_ATTR_2 = plus_status{}
    LIST_ATTR_5 = inonderzoek{}
    LIST_ATTR_8 = lv_publicatiedatum{}
    LIST_ATTR_7 = bgt_status{}
    LIST_ATTR_3 = imgeo_identificatie{}
    LIST_ATTR_6 = tijdstipregistratie{}
    LIST_ATTR_9 = relatievehoogteligging{}
    LIST_ATTR_4 = bronhouder{}
    List_tijdstip_registratie_Elements -> Actualiteitsbepaler_34

Bookmark: Alleen Actuele data gaat door
Actualiteitsbepaler_16
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__16
Actualiteitsbepaler_17
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__17
Actualiteitsbepaler_18
    EINDREGISTRATIE = @Value(eindregistratie)
    OBJECTEINDTIJD = @Value(objecteindtijd)
    BGT_STATUS = @Value(bgt_status)
    BGT_Statuschecker_bestaand -> ListExploder_hoortbijtypeoverbrugging
Actualiteitsbepaler_19
    EINDREGISTRATIE = @Value(eindregistratie)
    OBJECTEINDTIJD = @Value(objecteindtijd)
    BGT_STATUS = @Value(bgt_status)
    BGT_Statuschecker_bestaand -> ListExploder_plusType_gebouwinstallatie
Actualiteitsbepaler_20
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__20
Actualiteitsbepaler_21
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__21
Actualiteitsbepaler_22
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__22
Actualiteitsbepaler_23
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__23
Actualiteitsbepaler_24
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__24
Actualiteitsbepaler_26
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__26
Actualiteitsbepaler_27
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__27
Actualiteitsbepaler_28
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__33
Actualiteitsbepaler_29
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__29
Actualiteitsbepaler_9
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__9
Actualiteitsbepaler_31
    EINDREGISTRATIE = @Value(eindregistratie)
    OBJECTEINDTIJD = @Value(objecteindtijd)
    BGT_STATUS = @Value(bgt_status)
    BGT_Statuschecker_bestaand -> ListExploder_identificatiebagpnd_2
Actualiteitsbepaler
    EINDREGISTRATIE = @Value(eindregistratie)
    OBJECTEINDTIJD = @Value(objecteindtijd)
    BGT_STATUS = @Value(bgt_status)
    BGT_Statuschecker_bestaand -> ListExploder_identificatiebagpnd
Actualiteitsbepaler_2
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__4
Actualiteitsbepaler_3
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__5
Actualiteitsbepaler_4
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__2
Actualiteitsbepaler_10
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__10
Actualiteitsbepaler_5
    EINDREGISTRATIE = @Value(eindregistratie)
    OBJECTEINDTIJD = @Value(objecteindtijd)
    BGT_STATUS = @Value(bgt_status)
    BGT_Statuschecker_bestaand -> ListExploder_bgtFunctie
Actualiteitsbepaler_6
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__6
Actualiteitsbepaler_11
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__11
Actualiteitsbepaler_7
    EINDREGISTRATIE = @Value(eindregistratie)
    OBJECTEINDTIJD = @Value(objecteindtijd)
    BGT_STATUS = @Value(bgt_status)
    BGT_Statuschecker_bestaand -> ListExploder_plus_functie_Vegetatie
Actualiteitsbepaler_8
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__8
Actualiteitsbepaler_12
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__12
Actualiteitsbepaler_14
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__14
Actualiteitsbepaler_39
    EINDREGISTRATIE = @Value(eindregistratie)
    OBJECTEINDTIJD = @Value(objecteindtijd)
    BGT_STATUS = @Value(bgt_status)
    BGT_Statuschecker_bestaand -> ListExploder_opTalud_6
Actualiteitsbepaler_32
    EINDREGISTRATIE = @Value(eindregistratie)
    OBJECTEINDTIJD = @Value(objecteindtijd)
    BGT_STATUS = @Value(bgt_status)
    BGT_Statuschecker_bestaand -> ListExploder_bgtFunctie_Wegdeel_3
Actualiteitsbepaler_38
    EINDREGISTRATIE = @Value(eindregistratie)
    OBJECTEINDTIJD = @Value(objecteindtijd)
    BGT_STATUS = @Value(bgt_status)
    BGT_Statuschecker_bestaand -> ListExploder_opTalud_5
Actualiteitsbepaler_33
    EINDREGISTRATIE = @Value(eindregistratie)
    OBJECTEINDTIJD = @Value(objecteindtijd)
    BGT_STATUS = @Value(bgt_status)
    BGT_Statuschecker_bestaand -> ListExploder_bgtFunctie_Wegdeel_4
Actualiteitsbepaler_36
    EINDREGISTRATIE = @Value(eindregistratie)
    OBJECTEINDTIJD = @Value(objecteindtijd)
    BGT_STATUS = @Value(bgt_status)
    BGT_Statuschecker_bestaand -> ListExploder_optalud_begroeidterreindeel_3
Actualiteitsbepaler_35
    EINDREGISTRATIE = @Value(eindregistratie)
    OBJECTEINDTIJD = @Value(objecteindtijd)
    BGT_STATUS = @Value(bgt_status)
    BGT_Statuschecker_bestaand -> ListExploder_optalud_begroeidterreindeel_2
Actualiteitsbepaler_37
    EINDREGISTRATIE = @Value(eindregistratie)
    OBJECTEINDTIJD = @Value(objecteindtijd)
    BGT_STATUS = @Value(bgt_status)
    BGT_Statuschecker_bestaand -> AttributeManager_6
Actualiteitsbepaler_34
    EINDREGISTRATIE = @Value(eindregistratie)
    OBJECTEINDTIJD = @Value(objecteindtijd)
    BGT_STATUS = @Value(bgt_status)
    BGT_Statuschecker_bestaand -> Verwijder_attributen_uit_Listexploders_en_zet_attributen_volgens_definitie__in_onderzoek_en_plus-status__34

Bookmark: Verwijder attributen uit listexploders en maak klaar voor wegschrijven
Note: Verwijder_attributen_uit_Listexploders_en_zet_attributen_volgens_definitie__in_onderzoek_en_plus-status_
Verwijder_attributen_uit_Listexploders_en_zet_attributen_volgens_definitie__in_onderzoek_en_plus-status__16: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_bak (writer POSTGIS_1)
Note: Verwijder_attributen_uit_Listexploders_en_zet_attributen_volgens_definitie__in_onderzoek_en_plus-status_
Verwijder_attributen_uit_Listexploders_en_zet_attributen_volgens_definitie__in_onderzoek_en_plus-status__17: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_bord (writer POSTGIS_1)
Note: Verwijder_attributen_uit_Listexploders_en_zet_attributen_volgens_definitie__in_onderzoek_en_plus-status_
Verwijder_attributen_uit_Listexploders_en_zet_attributen_volgens_definitie__in_onderzoek_en_plus-status__18: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO hoortbijtypeoverbrugging = FME_CONDITIONAL:DEFAULT_VALUE'_FME_NO_OP_'BOOL_OP;OR;COMPOSITE_TEST;<Unused>;TEST @Value(hoortbijtypeoverbrugging) = waardeOnbekend'onbekend'FME_NUM_CONDITIONS2___
      SET_TO overbruggingisbeweegbaar = FME_CONDITIONAL:DEFAULT_VALUE'FME_NULL_VALUE'BOOL_OP;OR;COMPOSITE_TEST;<Unused>;TEST @Value(overbruggingisbeweegbaar) = false'N'BOOL_OP;OR;COMPOSITE_TEST;<Unused>;TEST @Value(overbruggingisbeweegbaar) = true'J'FME_NUM_CONDITIONS3___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.bgt_overbruggingsdeel (writer POSTGIS_1)
Note: Verwijder_attributen_uit_Listexploders_en_zet_attributen_volgens_definitie__in_onderzoek_en_plus-status_
Verwijder_attributen_uit_Listexploders_en_zet_attributen_volgens_definitie__in_onderzoek_en_plus-status__19: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_gebouwinstallatie (writer POSTGIS_1)
Note: Verwijder_attributen_uit_Listexploders_en_zet_attributen_volgens_definitie__in_onderzoek_en_plus-status_
Verwijder_attributen_uit_Listexploders_en_zet_attributen_volgens_definitie__in_onderzoek_en_plus-status__20: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'BOOL_OP;OR;COMPOSITE_TEST;<Unused>;TEST @Value(naam) = Halte'halte'FME_NUM_CONDITIONS3___
      SET_TO naam = FME_CONDITIONAL:DEFAULT_VALUE'_FME_NO_OP_'BOOL_OP;OR;COMPOSITE_TEST;<Unused>;TEST @Value(plus_type) = halte'FME_NULL_VALUE'FME_NUM_CONDITIONS2___
    -> imgeo.imgeo_functioneelgebied (writer POSTGIS_1)
Note: Verwijder_attributen_uit_Listexploders_en_zet_attributen_volgens_definitie__in_onderzoek_en_plus-status_
Verwijder_attributen_uit_Listexploders_en_zet_attributen_volgens_definitie__in_onderzoek_en_plus-status__21: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_installatie (writer POSTGIS_1)
Note: Verwijder_attributen_uit_Listexploders_en_zet_attributen_volgens_definitie__in_onderzoek_en_plus-status_
Verwijder_attributen_uit_Listexploders_en_zet_attributen_volgens_definitie__in_onderzoek_en_plus-status__22: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_kast (writer POSTGIS_1)
Note: Verwijder_attributen_uit_Listexploders_en_zet_attributen_volgens_definitie__in_onderzoek_en_plus-status_
Verwijder_attributen_uit_Listexploders_en_zet_attributen_volgens_definitie__in_onderzoek_en_plus-status__23: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_kunstwerkdeel (writer POSTGIS_1)
Note: Verwijder_attributen_uit_Listexploders_en_zet_attributen_volgens_definitie__in_onderzoek_en_plus-status_
Verwijder_attributen_uit_Listexploders_en_zet_attributen_volgens_definitie__in_onderzoek_en_plus-status__24: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_mast (writer POSTGIS_1)
Note: Verwijder_attributen_uit_Listexploders_en_zet_attributen_volgens_definitie__in_onderzoek_en_plus-status_
Verwijder_attributen_uit_Listexploders_en_zet_attributen_volgens_definitie__in_onderzoek_en_plus-status__26: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = geenWaarde'FME_NULL_VALUE'FME_NUM_CONDITIONS2___
    -> imgeo.bgt_ondersteunendwaterdeel (writer POSTGIS_1)
Note: Verwijder_attributen_uit_Listexploders_en_zet_attributen_volgens_definitie__in_onderzoek_en_plus-status_
Verwijder_attributen_uit_Listexploders_en_zet_attributen_volgens_definitie__in_onderzoek_en_plus-status__27: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
    -> imgeo.bgt_ongeclassificeerdobject (writer POSTGIS_1)
Note: Verwijder_attributen_uit_Listexploders_en_zet_attributen_volgens_definitie__in_onderzoek_en_plus-status_
Verwijder_attributen_uit_Listexploders_en_zet_attributen_volgens_definitie__in_onderzoek_en_plus-status__33: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      REMOVE label_tekst
      RENAME_SET_VALUE openbareruimte_type > openbareruimtetype
      REMOVE pos
      REMOVE _opr_labeltekst
      REMOVE _opr_labelpos
      REMOVE _opr_labelhoek
    -> DuplicateFilter_2
DuplicateFilter_2
    KEYATTR = inonderzoek openbareruimtetype eindregistratie opr_label_hoek objectbegintijd identificatie_namespace tijdstipregistratie identificatieBAGOPR lv_publicatiedatum relatievehoogteligging opr_label_tekst bgt_status bronhouder plus_status objecteindtijd opr_labelpos identificatie_lokaalid
    INPUT_ORDERED_CHOICE = No
    UNIQUE -> imgeo.bgt_openbareruimtelabel (writer POSTGIS_1)
Note: Verwijder_attributen_uit_Listexploders_en_zet_attributen_volgens_definitie__in_onderzoek_en_plus-status_
Verwijder_attributen_uit_Listexploders_en_zet_attributen_volgens_definitie__in_onderzoek_en_plus-status__29: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_overigbouwwerk (writer POSTGIS_1)
Note: Verwijder_attributen_uit_Listexploders_en_zet_attributen_volgens_definitie__in_onderzoek_en_plus-status_
Verwijder_attributen_uit_Listexploders_en_zet_attributen_volgens_definitie__in_onderzoek_en_plus-status__9: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_overigescheiding (writer POSTGIS_1)
Note: Verwijder_attributen_uit_Listexploders_en_zet_attributen_volgens_definitie__in_onderzoek_en_plus-status_
Verwijder_attributen_uit_Listexploders_en_zet_attributen_volgens_definitie__in_onderzoek_en_plus-status__32: AttributeManager
    ATTR_TABLE:
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      RENAME_SET_VALUE imgeo_nen3610_id_imgeo_namespace > identificatie_namespace
      REMOVE imgeo_nummeraanduidingreeks_imgeo_nummeraanduidingreeks
      RENAME_SET_VALUE imgeo_nummeraanduidingreeks_imgeo_identificatie_bagvbolaagste_huisnummer > identificatieBAGVBOLaagsteHuisnummer
      RENAME_SET_VALUE imgeo_nummeraanduidingreeks_imgeo_identificatie_bagvbohoogste_huisnummer > identificatieBAGVBOHoogsteHuisnummer
      REMOVE _num_index
      RENAME_SET_VALUE tekst_huisnummerReeks > tekst
      REMOVE plaatingspunt_hnr
      RENAME_SET_VALUE hoek_hnr > hnr_label_hoek
      REMOVE label_wkt
      RENAME_SET_VALUE imgeo_nen3610_id_imgeo_lokaal_id > identificatie_lokaalid
      REMOVE gml_id
      RENAME_SET_VALUE identificatiebagpnd > identificatieBAGPND
    -> DuplicateFilter_4
Note: Verwijder_attributen_uit_Listexploders_en_zet_attributen_volgens_definitie__in_onderzoek_en_plus-status_
Verwijder_attributen_uit_Listexploders_en_zet_attributen_volgens_definitie__in_onderzoek_en_plus-status_: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
    -> imgeo.bgt_pand (writer POSTGIS_1)
Note: Verwijder_attributen_uit_Listexploders_en_zet_attributen_volgens_definitie__in_onderzoek_en_plus-status_
Verwijder_attributen_uit_Listexploders_en_zet_attributen_volgens_definitie__in_onderzoek_en_plus-status__4: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_paal (writer POSTGIS_1)
Note: Verwijder_attributen_uit_Listexploders_en_zet_attributen_volgens_definitie__in_onderzoek_en_plus-status_
Verwijder_attributen_uit_Listexploders_en_zet_attributen_volgens_definitie__in_onderzoek_en_plus-status__5: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_put (writer POSTGIS_1)
Note: Verwijder_attributen_uit_Listexploders_en_zet_attributen_volgens_definitie__in_onderzoek_en_plus-status_
Verwijder_attributen_uit_Listexploders_en_zet_attributen_volgens_definitie__in_onderzoek_en_plus-status__2: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_scheiding (writer POSTGIS_1)
Note: Verwijder_attributen_uit_Listexploders_en_zet_attributen_volgens_definitie__in_onderzoek_en_plus-status_
Verwijder_attributen_uit_Listexploders_en_zet_attributen_volgens_definitie__in_onderzoek_en_plus-status__10: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_sensor (writer POSTGIS_1)
Note: Verwijder_attributen_uit_Listexploders_en_zet_attributen_volgens_definitie__in_onderzoek_en_plus-status_
Verwijder_attributen_uit_Listexploders_en_zet_attributen_volgens_definitie__in_onderzoek_en_plus-status__3: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO bgt_functie = FME_CONDITIONAL:DEFAULT_VALUE'_FME_NO_OP_'BOOL_OP;AND;COMPOSITE_TEST;<Unused>;TEST @Value(plus_functie) != "''";TEST @Value(plus_functie) ATTRIBUTE_HAS_VALUE _FME_BLANK_STRING_'niet-bgt'FME_NUM_CONDITIONS2___
      SET_TO plus_functie = FME_CONDITIONAL:DEFAULT_VALUE'_FME_NO_OP_'BOOL_OP;OR;COMPOSITE_TEST;<Unused>;TEST @Value(plus_functie) = "''";TEST @Value(plus_functie) = '';TEST plus_functie ATTRIBUTE_IS_EMPTY _FME_BLANK_STRING_'FME_NULL_VALUE'FME_NUM_CONDITIONS2___
    -> imgeo.imgeo_spoor (writer POSTGIS_1)
Note: Verwijder_attributen_uit_Listexploders_en_zet_attributen_volgens_definitie__in_onderzoek_en_plus-status_
Verwijder_attributen_uit_Listexploders_en_zet_attributen_volgens_definitie__in_onderzoek_en_plus-status__6: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.imgeo_straatmeubilair (writer POSTGIS_1)
Note: Verwijder_attributen_uit_Listexploders_en_zet_attributen_volgens_definitie__in_onderzoek_en_plus-status_
Verwijder_attributen_uit_Listexploders_en_zet_attributen_volgens_definitie__in_onderzoek_en_plus-status__11: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
    -> imgeo.bgt_tunneldeel (writer POSTGIS_1)
Note: Verwijder_attributen_uit_Listexploders_en_zet_attributen_volgens_definitie__in_onderzoek_en_plus-status_
Verwijder_attributen_uit_Listexploders_en_zet_attributen_volgens_definitie__in_onderzoek_en_plus-status__7: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_type = FME_CONDITIONAL:DEFAULT_VALUE'_FME_NO_OP_'BOOL_OP;OR;COMPOSITE_TEST;<Unused>;TEST @Value(plus_type) = waardeOnbekend'onbekend'FME_NUM_CONDITIONS2___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
    -> imgeo.imgeo_vegetatieobject (writer POSTGIS_1)
Note: Verwijder_attributen_uit_Listexploders_en_zet_attributen_volgens_definitie__in_onderzoek_en_plus-status_
Verwijder_attributen_uit_Listexploders_en_zet_attributen_volgens_definitie__in_onderzoek_en_plus-status__8: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      SET_TO plus_type = FME_CONDITIONAL:DEFAULT_VALUE'_FME_NO_OP_'BOOL_OP;OR;COMPOSITE_TEST;<Unused>;TEST @Value(plus_type) = waardeOnbekend'onbekend'FME_NUM_CONDITIONS2___
    -> imgeo.bgt_waterdeel (writer POSTGIS_1)
Note: Verwijder_attributen_uit_Listexploders_en_zet_attributen_volgens_definitie__in_onderzoek_en_plus-status_
Verwijder_attributen_uit_Listexploders_en_zet_attributen_volgens_definitie__in_onderzoek_en_plus-status__12: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_type = FME_CONDITIONAL:DEFAULT_VALUE'_FME_NO_OP_'BOOL_OP;OR;COMPOSITE_TEST;<Unused>;TEST @Value(plus_type) = waardeOnbekend'onbekend'FME_NUM_CONDITIONS2___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
    -> imgeo.imgeo_waterinrichtingselement (writer POSTGIS_1)
Note: Verwijder_attributen_uit_Listexploders_en_zet_attributen_volgens_definitie__in_onderzoek_en_plus-status_
Verwijder_attributen_uit_Listexploders_en_zet_attributen_volgens_definitie__in_onderzoek_en_plus-status__14: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_type = FME_CONDITIONAL:DEFAULT_VALUE'_FME_NO_OP_'BOOL_OP;OR;COMPOSITE_TEST;<Unused>;TEST @Value(plus_type) = waardeOnbekend'onbekend'FME_NUM_CONDITIONS2___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
    -> imgeo.imgeo_weginrichtingselement (writer POSTGIS_1)
Note: Verwijder_attributen_uit_Listexploders_en_zet_attributen_volgens_definitie__in_onderzoek_en_plus-status_
Verwijder_attributen_uit_Listexploders_en_zet_attributen_volgens_definitie__in_onderzoek_en_plus-status__37: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_fysiekvoorkomen = FME_CONDITIONAL:DEFAULT_VALUE'_FME_NO_OP_'BOOL_OP;OR;COMPOSITE_TEST;<Unused>;TEST @Value(plus_fysiekvoorkomen) = waardeOnbekend'onbekend'FME_NUM_CONDITIONS2___
      SET_TO optalud = FME_CONDITIONAL:DEFAULT_VALUE'N'BOOL_OP;OR;COMPOSITE_TEST;<Unused>;TEST @UpperCase(@Value(optalud)) = TRUE'J'BOOL_OP;OR;COMPOSITE_TEST;<Unused>;TEST @UpperCase(@Value(optalud)) = FALSE'N'FME_NUM_CONDITIONS3___
      SET_TO plus_functie = FME_CONDITIONAL:DEFAULT_VALUE'_FME_NO_OP_'BOOL_OP;OR;COMPOSITE_TEST;<Unused>;TEST @Value(plus_functie) = waardeOnbekend'onbekend'FME_NUM_CONDITIONS2___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      REMOVE _opTalud_index
    -> imgeo.bgt_wegdeel (writer POSTGIS_1)
Note: Verwijder_attributen_uit_Listexploders_en_zet_attributen_volgens_definitie__in_onderzoek_en_plus-status_
Verwijder_attributen_uit_Listexploders_en_zet_attributen_volgens_definitie__in_onderzoek_en_plus-status__28: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_fysiekvoorkomen = FME_CONDITIONAL:DEFAULT_VALUE'_FME_NO_OP_'BOOL_OP;OR;COMPOSITE_TEST;<Unused>;TEST @Value(plus_fysiekvoorkomen) = waardeOnbekend'onbekend'FME_NUM_CONDITIONS2___
      SET_TO optalud = FME_CONDITIONAL:DEFAULT_VALUE'N'BOOL_OP;OR;COMPOSITE_TEST;<Unused>;TEST @UpperCase(@Value(optalud)) = TRUE'J'BOOL_OP;OR;COMPOSITE_TEST;<Unused>;TEST @UpperCase(@Value(optalud)) = FALSE'N'FME_NUM_CONDITIONS3___
      SET_TO plus_functie = FME_CONDITIONAL:DEFAULT_VALUE'_FME_NO_OP_'BOOL_OP;OR;COMPOSITE_TEST;<Unused>;TEST @Value(plus_functie) = waardeOnbekend'onbekend'FME_NUM_CONDITIONS2___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
    -> imgeo.bgt_ondersteunendwegdeel (writer POSTGIS_1)
Note: Verwijder_attributen_uit_Listexploders_en_zet_attributen_volgens_definitie__in_onderzoek_en_plus-status_
Verwijder_attributen_uit_Listexploders_en_zet_attributen_volgens_definitie__in_onderzoek_en_plus-status__35: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_fysiekvoorkomen = FME_CONDITIONAL:DEFAULT_VALUE'_FME_NO_OP_'BOOL_OP;OR;COMPOSITE_TEST;<Unused>;TEST @Value(plus_fysiekvoorkomen) = waardeOnbekend'onbekend'FME_NUM_CONDITIONS2___
      SET_TO optalud = FME_CONDITIONAL:DEFAULT_VALUE'N'BOOL_OP;OR;COMPOSITE_TEST;<Unused>;TEST @UpperCase(@Value(optalud)) = TRUE'J'BOOL_OP;OR;COMPOSITE_TEST;<Unused>;TEST @UpperCase(@Value(optalud)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
    -> imgeo.bgt_begroeidterreindeel (writer POSTGIS_1)
Note: Verwijder_attributen_uit_Listexploders_en_zet_attributen_volgens_definitie__in_onderzoek_en_plus-status_
Verwijder_attributen_uit_Listexploders_en_zet_attributen_volgens_definitie__in_onderzoek_en_plus-status__36: AttributeManager
    ATTR_TABLE:
      RENAME_SET_VALUE identificatie_lokaal_id > identificatie_lokaalid
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO optalud = FME_CONDITIONAL:DEFAULT_VALUE'N'BOOL_OP;OR;COMPOSITE_TEST;<Unused>;TEST @UpperCase(@Value(optalud)) = TRUE'J'BOOL_OP;OR;COMPOSITE_TEST;<Unused>;TEST @UpperCase(@Value(optalud)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      RENAME_SET_VALUE horend_bij > objectklasse_kruinlijn
    -> imgeo.bgt_kruinlijn (writer POSTGIS_1)
Note: Verwijder_attributen_uit_Listexploders_en_zet_attributen_volgens_definitie__in_onderzoek_en_plus-status_
Verwijder_attributen_uit_Listexploders_en_zet_attributen_volgens_definitie__in_onderzoek_en_plus-status__34: AttributeManager
    ATTR_TABLE:
      RENAME_SET_VALUE identificatie_lokaal_id > identificatie_lokaalid
      REMOVE _element_index
      REMOVE fme_rejection_code
      SET_TO inonderzoek = FME_CONDITIONAL:DEFAULT_VALUE'FME_NULL_VALUE'BOOL_OP;OR;COMPOSITE_TEST;<Unused>;TEST @UpperCase(@Value(inonderzoek)) = TRUE'J'BOOL_OP;OR;COMPOSITE_TEST;<Unused>;TEST @UpperCase(@Value(inonderzoek)) = FALSE'N'FME_NUM_CONDITIONS3___
      SET_TO plus_fysiekvoorkomen = FME_CONDITIONAL:DEFAULT_VALUE'_FME_NO_OP_'BOOL_OP;OR;COMPOSITE_TEST;<Unused>;TEST @Value(plus_fysiekvoorkomen) = waardeOnbekend'onbekend'FME_NUM_CONDITIONS2___
      SET_TO optalud = FME_CONDITIONAL:DEFAULT_VALUE'N'BOOL_OP;OR;COMPOSITE_TEST;<Unused>;TEST @UpperCase(@Value(optalud)) = TRUE'J'BOOL_OP;OR;COMPOSITE_TEST;<Unused>;TEST @UpperCase(@Value(optalud)) = FALSE'N'FME_NUM_CONDITIONS3___
      SET_TO plus_status = FME_CONDITIONAL:DEFAULT_VALUE'_FME_NO_OP_'BOOL_OP;OR;COMPOSITE_TEST;<Unused>;TEST @Value(plus_status) = geenWaarde'FME_NULL_VALUE'FME_NUM_CONDITIONS2___
      REMOVE fme_geometry
      REMOVE _geometry_name
      REMOVE _part_number
    -> imgeo.bgt_onbegroeidterreindeel (writer POSTGIS_1)

Bookmark: Wegschrijven_objecten
imgeo.imgeo_bak (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.imgeo_bord (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.bgt_overbruggingsdeel (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), plus_type varchar(200), hoortbijtypeoverbrugging varchar(200), overbruggingisbeweegbaar varchar(1)
imgeo.imgeo_gebouwinstallatie (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.imgeo_functioneelgebied (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200), naam varchar(200)
imgeo.imgeo_installatie (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.imgeo_kast (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.imgeo_kunstwerkdeel (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.imgeo_mast (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.bgt_ondersteunendwaterdeel (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.bgt_ongeclassificeerdobject (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8)
imgeo.bgt_openbareruimtelabel (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), identificatiebagopr varchar(20), openbareruimtetype varchar(200), opr_label_tekst varchar(200), opr_label_hoek float4
imgeo.imgeo_overigbouwwerk (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.imgeo_overigescheiding (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
DuplicateFilter_4
    KEYATTR = hnr_label_hoek tijdstipregistratie objecteindtijd identificatieBAGVBOHoogsteHuisnummer identificatie_namespace identificatieBAGPND identificatieBAGVBOLaagsteHuisnummer bronhouder lv_publicatiedatum objectbegintijd bgt_status identificatie_lokaalid inonderzoek relatievehoogteligging plus_status eindregistratie tekst
    INPUT_ORDERED_CHOICE = No
    UNIQUE -> AttributeSplitterKoppelteken
Note: geometrie: postgis_ geometrie
imgeo.bgt_pand (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), identificatiebagpnd varchar(20)
imgeo.imgeo_paal (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), hectometeraanduiding varchar(200), plus_type varchar(200)
imgeo.bgt_plaatsbepalingspunt (writer POSTGIS_1) [off]
    attributes: nen3610_id_imgeo_namespace varchar(200), nen3610_id_imgeo_lokaal_id varchar(200), nauwkeurigheid varchar(200), datuminwinning varchar(200), inwinnendeinstantie varchar(200), inwinningsmethode varchar(200)
imgeo.imgeo_put (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.imgeo_scheiding (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.imgeo_sensor (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.imgeo_spoor (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_functie varchar(200), plus_functie varchar(200)
imgeo.imgeo_straatmeubilair (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), plus_type varchar(200), bgt_type varchar(200)
imgeo.bgt_tunneldeel (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8)
imgeo.imgeo_vegetatieobject (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), plus_type varchar(200), bgt_type varchar(200)
imgeo.bgt_waterdeel (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.imgeo_waterinrichtingselement (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_type varchar(200), plus_type varchar(200)
imgeo.imgeo_weginrichtingselement (writer POSTGIS_1)
    attributes: identificatie_namespace varchar(8), identificatie_lokaalid varchar(38), objectbegintijd date, objecteindtijd date, eindregistratie timestamp, tijdstipregistratie timestamp, lv_publicatiedatum timestamp, bronhouder varchar(40), inonderzoek varchar(1), relatievehoogteligging int2, bgt_status varchar(8), plus_status varchar(8), bgt_type varchar(200), plus_type varchar(200)
imgeo.bgt_wegdeel (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_functie varchar(200), bgt_fysiekvoorkomen varchar(200), optalud varchar(1), plus_functie varchar(200), plus_fysiekvoorkomen varchar(200)
imgeo.bgt_ondersteunendwegdeel (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_functie varchar(200), bgt_fysiekvoorkomen varchar(200), optalud varchar(1), plus_functie varchar(200), plus_fysiekvoorkomen varchar(200)
imgeo.bgt_begroeidterreindeel (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_fysiekvoorkomen varchar(200), optalud varchar(1), plus_fysiekvoorkomen varchar(200)
imgeo.bgt_kruinlijn (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), optalud varchar(1), objectklasse_kruinlijn varchar(200)
imgeo.bgt_onbegroeidterreindeel (writer POSTGIS_1)
    attributes: identificatie_namespace varchar(8), identificatie_lokaalid varchar(38), objectbegintijd date, objecteindtijd date, tijdstipregistratie timestamp, eindregistratie timestamp, lv_publicatiedatum timestamp, bronhouder varchar(40), inonderzoek varchar(1), relatievehoogteligging int2, bgt_status varchar(8), plus_status varchar(8), bgt_fysiekvoorkomen varchar(200), optalud varchar(1), plus_fysiekvoorkomen varchar(200)

Bookmark: Bepalen wat een huisnummerreeks is en daarna de reeks uitsplitsen in een _list
Note: huisnummerreeksen splitsen op basis van een koppelteken '-' en tot een _list verwerken / bijvoorbeeld 33A-33F wordt gesplits in: / 33A / 33F
AttributeSplitterKoppelteken
    DROP_EMPTY_PARTS = No
    ATTR_NAME = tekst
    LIST_NAME = _list
    DELIMITER = -
    TRIM_OPTION = None
    -> ListElementCounter
Note: ListElementCounter: tel aantal list_element_num in _list
ListElementCounter
    LIST_NAME = _list{}
    CNT_ATTR = _element_count
    -> Tester
Note: Bepalen wat een reeks is op basis het aantal element_num in _list. / Enkele huisnr (geen reeks) hebben 1 element_num in de _list.
Tester
    TEST_CLAUSE = TEST @Value(_element_count) = 1
    TEST_MODE = Automatic
    TEST_DESCRIPTION = ""
    BOOL_OP = OR
    FAILED -> ListExploder:_list
    PASSED -> AttributeManager_12

Bookmark: New Bookmark
Note: geen koppelteken: / 33 33 / 33A 33A / 33/1 33/1
AttributeManager_12
    ATTR_TABLE:
      SET_TO tekst_afgekort = @Value(tekst)
      REMOVE _list{}
      REMOVE _element_count
    -> imgeo.bgt_nummeraanduidingreeks (writer POSTGIS_2)

Bookmark: Huisnummer en letters mogen niet leeg zijn
Note: Testen of huisnummer een waarde heeft?
Tester_4
    TEST_CLAUSE = TEST @Value(huisnummer) ATTRIBUTE_HAS_VALUE ""
    TEST_MODE = Automatic
    TEST_DESCRIPTION = ""
    BOOL_OP = OR
    PASSED -> Matcher_2
    FAILED -> Tester_2
Note: Testen of huisletter een waarde heeft?
Tester_2
    TEST_CLAUSE = TEST @Value(huisletter) ATTRIBUTE_HAS_VALUE ""
    TEST_MODE = Automatic
    TEST_DESCRIPTION = ""
    BOOL_OP = OR
    PASSED -> Matcher_2

Bookmark: Bepalen huisnummers en huisletters van 1e en 2e deel in reeks en in een _lijst stoppen
Note: Bepalen waar een huisletter is op basis van firstmatch en lokaalid en / waarbij element_index uniek moet zijn. Bij de singlematch wordt dit in list_ gezet.
Matcher_2
    MATCH_STRATEGY = Match Selected Attributes
    LENIENT_MATCH = No
    MATCH = 2D
    CNT_ATTR = _match_id
    BLANK_AND_MISSING_DIFFER = No
    DIFFATTRS = _element_index_2
    SM_LIST_NAME = lijst_
    MATCHATTRS = _first_match identificatie_lokaalid
    SINGLE_MATCHED -> ListIndexer
    NOT_MATCHED -> AttributeRemover
Note: ListIndexer: lijst_ indexeren op 1 en schrift het werg als lijst2
ListIndexer
    LIST_ATTR = lijst_{}
    PREFIX = lijst2
    INDEX = 1
    -> AttributeManager_11
Note: lijst2huislletter wordt nieuwe huisletter
AttributeManager_11
    ATTR_TABLE:
      REMOVE _element_count
      REMOVE part
      REMOVE _element_index_2
      REMOVE huisletter
      REMOVE lijst_{}.objectbegintijd
      REMOVE lijst_{}.objecteindtijd
      REMOVE lijst_{}.eindregistratie
      REMOVE lijst_{}.bronhouder
      REMOVE lijst_{}.tijdstipregistratie
      REMOVE lijst_{}.inonderzoek
      REMOVE lijst_{}.relatievehoogteligging
      REMOVE lijst_{}.lv_publicatiedatum
      REMOVE lijst_{}.bgt_status
      REMOVE lijst_{}.plus_status
      REMOVE lijst_{}.identificatie_namespace
      REMOVE lijst_{}.tekst
      REMOVE lijst_{}.hnr_label_hoek
      REMOVE lijst_{}.identificatie_lokaalid
      REMOVE lijst_{}._list
      REMOVE lijst_{}._element_count
      REMOVE lijst_{}._element_index
      REMOVE lijst_{}._first_match
      REMOVE lijst_{}.part
      REMOVE lijst_{}._element_index_2
      REMOVE lijst_{}.huisnummer
      REMOVE lijst_{}.huisletter
      REMOVE _match_id
      REMOVE lijst2objectbegintijd
      REMOVE lijst2objecteindtijd
      REMOVE lijst2eindregistratie
      REMOVE lijst2bronhouder
      REMOVE lijst2tijdstipregistratie
      REMOVE lijst2inonderzoek
      REMOVE lijst2relatievehoogteligging
      REMOVE lijst2lv_publicatiedatum
      REMOVE lijst2bgt_status
      REMOVE lijst2plus_status
      REMOVE lijst2identificatie_namespace
      REMOVE lijst2tekst
      REMOVE lijst2hnr_label_hoek
      REMOVE lijst2identificatie_lokaalid
      REMOVE lijst2_list
      REMOVE lijst2_element_count
      REMOVE lijst2_element_index
      REMOVE lijst2_first_match
      REMOVE lijst2part
      REMOVE lijst2_element_index_2
      REMOVE lijst2huisnummer
      RENAME_SET_VALUE lijst2huisletter > huisletter
    -> AttributeRemover
Note: AttributeRemover: verwijderen onnodige attributen
Note: bepalen gelijke huisnrs in 1e deel en 2e deel in huisnummerreeks / op basis van huisnummer en indentificatie_lokaalid en waarbij element_index ongelijk is en zet dit in lijst3
AttributeRemover
    REMOVE_ATTRS = part,_element_index_2,_element_count,_match_id
    -> Matcher_gelijke_huisnummer

Bookmark: Gelijke huisnummers in reeks
Note: testen of in lijst3 een huisletter voorkomt
Note: koppelteken, gelijke (huisnummer) / 33A-33F 33A-F / 33/1-33/20 33 / 33A/1–33A/20 33A / 33A/1A-33A/3F 33A
TesterHuisletterIsGevuld
    TEST_CLAUSE = TEST @Value(lijst3{0}.huisletter) ATTRIBUTE_HAS_VALUE ""
    TEST_MODE = Automatic
    TEST_DESCRIPTION = ""
    BOOL_OP = OR
    PASSED -> ListSorter
    FAILED -> ListIndexer_2
Note: Bij een huisletter in lijst3 sorteer alphabetisch
ListSorter
    TYPE = Alphabetic
    ORDER = Ascending
    SRC_LIST = lijst3{}.huisletter
    -> ListIndexer_2
Note: Listindexer 0 vullen van lijst3 op prefex huisltr1
ListIndexer_2
    LIST_ATTR = lijst3{}
    PREFIX = huisltr1
    INDEX = 0
    -> ListIndexer_3
Note: Listindexer 1 vullen van lijst3 op prefex huisltr2
ListIndexer_3
    LIST_ATTR = lijst3{}
    PREFIX = huisltr2
    INDEX = 1
    -> AttributeKeeper
Note: huisletters in aparte attributen: huisletter1 en huisletter2
AttributeKeeper
    KEEP_ATTRS = objecteindtijd,inonderzoek,hnr_label_hoek,huisltr1huisletter,relatievehoogteligging,huisnummer,identificatie_namespace,identificatieBAGPND,bgt_status,identificatieBAGVBOHoogsteHuisnummer,bronhouder,identificatie_lokaalid,plus_status,lv_publicatiedatum,tijdstipregistratie,tekst,huisltr2huisletter,objectbegintijd,identificatieBAGVBOLaagsteHuisnummer,eindregistratie
    -> Testerhuisltr1_en_huisletter2_zijn_gevuld
Testerhuisltr1_en_huisletter2_zijn_gevuld
    TEST_CLAUSE:
      TEST @Value(huisltr1huisletter) ATTRIBUTE_HAS_VALUE ""
      TEST @Value(huisltr2huisletter) ATTRIBUTE_HAS_VALUE ""
    TEST_MODE = Automatic
    TEST_DESCRIPTION = ""
    BOOL_OP = AND
    PASSED -> Tester_huisletters_gelijk_zijn
    FAILED -> Testerhuisltr1_en_huisletter2_zijn_gevuld_3
Tester_huisletters_gelijk_zijn
    TEST_CLAUSE = TEST @Value(huisltr1huisletter) = @Value(huisltr2huisletter)
    TEST_MODE = Automatic
    TEST_DESCRIPTION = ""
    BOOL_OP = OR
    FAILED -> AttributeManager_3
    PASSED -> AttributeManager_2
Note: afkorting: 33A
AttributeManager_2
    ATTR_TABLE = SET_TO tekst_afgekort = @Value(huisnummer)@Value(huisltr1huisletter)
    -> AttributeRemover_3
Note: afkorting: 33A-F
AttributeManager_3
    ATTR_TABLE = SET_TO tekst_afgekort = @Value(huisnummer)@Value(huisltr1huisletter)-@Value(huisltr2huisletter)
    -> AttributeRemover_3
Testerhuisltr1_en_huisletter2_zijn_gevuld_3
    TEST_CLAUSE = TEST @Value(huisltr2huisletter) ATTRIBUTE_HAS_VALUE ""
    TEST_MODE = Automatic
    TEST_DESCRIPTION = ""
    BOOL_OP = AND
    PASSED -> AttributeManager_4
    FAILED -> AttributeManager_9
Note: afkorting: 33-33C
AttributeManager_4
    ATTR_TABLE = SET_TO tekst_afgekort = @Value(huisnummer)-@Value(huisnummer)@Value(huisltr2huisletter)
    -> AttributeRemover_3
Note: afkorting: 33 en 33A
AttributeManager_9
    ATTR_TABLE = SET_TO tekst_afgekort = @Value(huisnummer)@Value(huisltr1huisletter)
    -> AttributeRemover_3
AttributeRemover_3
    REMOVE_ATTRS = huisnummer,huisltr1huisletter,huisltr2huisletter
    -> imgeo.bgt_nummeraanduidingreeks (writer POSTGIS_2)

Bookmark: ongelijke huismummers in reeks waarbij de huisletters verdwijnen!
Note: Bepalen huisnummers op basis van tekst en lokaalid en zet dit in lijst4
Note: koppelteken, ongelijke (huisnummer) / 33-37 33-37 / 33A-37C 33-37 / 33/1-37/20 33-37 / 33A/1-37C/20 33-37 / 33A/1A-37C/3F 33-37
Matcherongelijkhuisnummers
    MATCH_STRATEGY = Match Selected Attributes
    LENIENT_MATCH = No
    MATCH = 2D
    CNT_ATTR = _match_id
    BLANK_AND_MISSING_DIFFER = No
    DIFFATTRS = _element_index
    SM_LIST_NAME = lijst4
    MATCHATTRS = identificatie_lokaalid tekst
    SINGLE_MATCHED -> ListSorterhuisnummers
Note: ListSorterhuisnummers lijst4.huisnummer
ListSorterhuisnummers
    TYPE = Numeric
    ORDER = Ascending
    SRC_LIST = lijst4{}.huisnummer
    -> ListIndexer_5
Note: ListIndexer0_vullen van lijst4 op prefix huisnr1_
ListIndexer_5
    LIST_ATTR = lijst4{}
    PREFIX = huisnr1_
    INDEX = 0
    -> ListIndex_vullenhuisnr2
Note: ListIndexer1_vullen van lijst4 op prefix huisnr2_
ListIndex_vullenhuisnr2: ListIndexer
    LIST_ATTR = lijst4{}
    PREFIX = huisnr2_
    INDEX = 1
    -> AttributeKeeper_2
Note: AttributeKeeper_2: huisnr1_huisnummer en huisnr2_huisnummer gaan oa mee
AttributeKeeper_2
    KEEP_ATTRS = objecteindtijd,inonderzoek,hnr_label_hoek,huisletter,huisnr1_huisnummer,huisnr2_huisnummer,relatievehoogteligging,identificatie_namespace,identificatieBAGPND,bgt_status,identificatieBAGVBOHoogsteHuisnummer,bronhouder,identificatie_lokaalid,plus_status,lv_publicatiedatum,tijdstipregistratie,tekst,objectbegintijd,identificatieBAGVBOLaagsteHuisnummer,eindregistratie
    -> AttributeManager_10
Note: 1e deel koppelteken '-' 2e deel reeks bv afkorting: 33-37
AttributeManager_10
    ATTR_TABLE:
      SET_TO tekst_afgekort = @Value(huisnr1_huisnummer)-@Value(huisnr2_huisnummer)
      REMOVE huisletter
    -> AttributeRemover_2
AttributeRemover_2
    REMOVE_ATTRS = huisnr2_huisnummer,huisnr1_huisnummer
    -> imgeo.bgt_nummeraanduidingreeks (writer POSTGIS_2)

Bookmark: Functie_ListExpplorer
Note: ListExploder_bgtFunctie
ListExploder_bgtFunctie
    LIST_ATTR = bgt_functie{}
    ATTR_CONFLICT_RES = Use Incoming List
    ATTR_ACCUM_MODE = Merge Incoming List
    INDEX_ATTR = _element_index
    ELEMENTS -> ListExploder_plus_functie
    <REJECTED> -> ListExploder_plus_functie
Note: ListExploder_bgtFunctie_Wegdeel
ListExploder_bgtFunctie_Wegdeel_3
    LIST_ATTR = bgt_functie{}
    ATTR_CONFLICT_RES = Use Incoming List
    ATTR_ACCUM_MODE = Merge Incoming List
    INDEX_ATTR = _element_index
    ELEMENTS -> ListExploder_PlusFunctie_4
    <REJECTED> -> ListExploder_PlusFunctie_4
Note: ListExploder_bgtFunctie_Wegdeel
ListExploder_bgtFunctie_Wegdeel_4
    LIST_ATTR = bgt_functie{}
    ATTR_CONFLICT_RES = Use Incoming List
    ATTR_ACCUM_MODE = Merge Incoming List
    INDEX_ATTR = _element_index
    ELEMENTS -> ListExploder_PlusFunctie_3
    <REJECTED> -> ListExploder_PlusFunctie_3

Bookmark: PlusFunctie_ListExplorer
Note: ListExploder_plus_functie
ListExploder_plus_functie
    LIST_ATTR = plus_functie{}
    ATTR_CONFLICT_RES = Use Incoming List
    ATTR_ACCUM_MODE = Merge Incoming List
    INDEX_ATTR = _element_index
    ELEMENTS -> Verwijder_attributen_uit_Listexploders_en_zet_attributen_volgens_definitie__in_onderzoek_en_plus-status__3
    <REJECTED> -> Verwijder_attributen_uit_Listexploders_en_zet_attributen_volgens_definitie__in_onderzoek_en_plus-status__3
Note: ListExploder_plus_functie_Vegetatie
ListExploder_plus_functie_Vegetatie
    LIST_ATTR = plus_type{}
    ATTR_CONFLICT_RES = Use Incoming List
    ATTR_ACCUM_MODE = Merge Incoming List
    INDEX_ATTR = _element_index
    ELEMENTS -> Verwijder_attributen_uit_Listexploders_en_zet_attributen_volgens_definitie__in_onderzoek_en_plus-status__7
    <REJECTED> -> Verwijder_attributen_uit_Listexploders_en_zet_attributen_volgens_definitie__in_onderzoek_en_plus-status__7
Note: ListExploder_PlusFunctie
ListExploder_PlusFunctie_4
    LIST_ATTR = plus_functie{}
    ATTR_CONFLICT_RES = Use Incoming List
    ATTR_ACCUM_MODE = Merge Incoming List
    INDEX_ATTR = _element_index
    ELEMENTS -> ListExploder_opTalud_3
    <REJECTED> -> ListExploder_opTalud_3
Note: ListExploder_PlusFunctie
ListExploder_PlusFunctie_3
    LIST_ATTR = plus_functie{}
    ATTR_CONFLICT_RES = Use Incoming List
    ATTR_ACCUM_MODE = Merge Incoming List
    INDEX_ATTR = _element_index
    ELEMENTS -> ListExploder_opTalud_4
    <REJECTED> -> ListExploder_opTalud_4

Bookmark: OpTalud_ListExplorer
Note: ListExploder_opTalud
ListExploder_opTalud_6
    LIST_ATTR = optalud{}
    ATTR_CONFLICT_RES = Use Incoming List
    ATTR_ACCUM_MODE = Merge Incoming List
    INDEX_ATTR = _opTalud_index
    ELEMENTS -> AttributeManager_7
    <REJECTED> -> AttributeManager_7
Note: ListExploder_opTalud
ListExploder_opTalud_3
    LIST_ATTR = optalud{}
    ATTR_CONFLICT_RES = Use Incoming List
    ATTR_ACCUM_MODE = Merge Incoming List
    INDEX_ATTR = _opTalud_index
    ELEMENTS -> ListExploder_PlusFysiekvoorkomen_3
    <REJECTED> -> ListExploder_PlusFysiekvoorkomen_3
Note: ListExploder_opTalud
ListExploder_opTalud_5
    LIST_ATTR = optalud{}
    ATTR_CONFLICT_RES = Use Incoming List
    ATTR_ACCUM_MODE = Merge Incoming List
    INDEX_ATTR = _element_index
    ELEMENTS -> AttributeManager_5
    <REJECTED> -> AttributeManager_5
Note: ListExploder_opTalud
ListExploder_opTalud_4
    LIST_ATTR = optalud{}
    ATTR_CONFLICT_RES = Use Incoming List
    ATTR_ACCUM_MODE = Merge Incoming List
    INDEX_ATTR = _element_index
    ELEMENTS -> ListExploder_PlusFysiekvoorkomen_4
    <REJECTED> -> ListExploder_PlusFysiekvoorkomen_4
Note: ListExploder_optalud_begroeidterreindeel
ListExploder_optalud_begroeidterreindeel_3
    LIST_ATTR = optalud{}
    ATTR_CONFLICT_RES = Use Incoming List
    ATTR_ACCUM_MODE = Merge Incoming List
    INDEX_ATTR = _element_index
    ELEMENTS -> AttributeManager_8
    <REJECTED> -> AttributeManager_8
Note: ListExploder_optalud_begroeidterreindeel
ListExploder_optalud_begroeidterreindeel_2
    LIST_ATTR = optalud{}
    ATTR_CONFLICT_RES = Use Incoming List
    ATTR_ACCUM_MODE = Merge Incoming List
    INDEX_ATTR = _element_index
    ELEMENTS -> ListExploder_plusfysiekvoorkomen_bergoeidterreindeel_2
    <REJECTED> -> ListExploder_plusfysiekvoorkomen_bergoeidterreindeel_2

Bookmark: PlusFysiekVoorkomen_ListExplorer
Note: ListExploder_PlusFysiekvoorkomen
ListExploder_PlusFysiekvoorkomen_3
    LIST_ATTR = plus_fysiekvoorkomen{}
    ATTR_CONFLICT_RES = Use Incoming List
    ATTR_ACCUM_MODE = Merge Incoming List
    INDEX_ATTR = _element_index
    ELEMENTS -> Verwijder_attributen_uit_Listexploders_en_zet_attributen_volgens_definitie__in_onderzoek_en_plus-status__37
    <REJECTED> -> Verwijder_attributen_uit_Listexploders_en_zet_attributen_volgens_definitie__in_onderzoek_en_plus-status__37
Note: ListExploder_PlusFysiekvoorkomen
ListExploder_PlusFysiekvoorkomen_4
    LIST_ATTR = plus_fysiekvoorkomen{}
    ATTR_CONFLICT_RES = Use Incoming List
    ATTR_ACCUM_MODE = Merge Incoming List
    INDEX_ATTR = _element_index
    ELEMENTS -> Verwijder_attributen_uit_Listexploders_en_zet_attributen_volgens_definitie__in_onderzoek_en_plus-status__28
    <REJECTED> -> Verwijder_attributen_uit_Listexploders_en_zet_attributen_volgens_definitie__in_onderzoek_en_plus-status__28
Note: ListExploder_plusfysiekvoorkomen_bergoeidterreindeel
ListExploder_plusfysiekvoorkomen_bergoeidterreindeel_2
    LIST_ATTR = plus_fysiekvoorkomen{}
    ATTR_CONFLICT_RES = Use Incoming List
    ATTR_ACCUM_MODE = Merge Incoming List
    INDEX_ATTR = _element_index
    ELEMENTS -> Verwijder_attributen_uit_Listexploders_en_zet_attributen_volgens_definitie__in_onderzoek_en_plus-status__35
    <REJECTED> -> Verwijder_attributen_uit_Listexploders_en_zet_attributen_volgens_definitie__in_onderzoek_en_plus-status__35

FME custom transformer Actualiteitsbepaler

Parameters:
- OBJECTEINDTIJD = @Value(objecteindtijd)   # objecteindtijd
- EINDREGISTRATIE = @Value(eindregistratie)   # eindregistratie
- BGT_STATUS = @Value(bgt_status)   # Bgt Status

eindregistratie_Input (input)
    -> eindregistratie
Note: eindregistratie, alleen de lege
Note: Aangezien er in de GML ook niet-actuele gegevens kunnen voorkomen, filteren we hier op
eindregistratie: AttributeFilter
    ATTR_NAME = eindregistratie
    ATTR_VALUES = <EMPTY>,<MISSING>,<NULL>,<UNFILTERED>
    <EMPTY> -> objecteindtijd
    <MISSING> -> objecteindtijd
    <NULL> -> objecteindtijd
Note: objecteindtijd, alleen de lege
objecteindtijd: AttributeFilter
    ATTR_NAME = objecteindtijd
    ATTR_VALUES = <EMPTY>,<MISSING>,<NULL>,<UNFILTERED>
    <EMPTY> -> BGT_Statuschecker
    <MISSING> -> BGT_Statuschecker
    <NULL> -> BGT_Statuschecker
Note: alleen status: bestaand
BGT_Statuschecker: AttributeFilter
    ATTR_NAME = bgt_status
    ATTR_VALUES = <EMPTY>,<MISSING>,<NULL>,<UNFILTERED>,bestaand
    bestaand -> BGT_Statuschecker_bestaand (output)
BGT_Statuschecker_bestaand (output)

FME custom transformer Generieke_attributen

Parameters:
- LIST_ATTR = eindregistratie{}   # "" List Attribute
- LIST_ATTR_2 = plus-status{}   # "" List Attribute
- LIST_ATTR_3 = imgeo_identificatie{}   # "" List Attribute
- LIST_ATTR_4 = bronhouder{}   # "" List Attribute
- LIST_ATTR_5 = in_onderzoek{}   # "" List Attribute
- LIST_ATTR_6 = tijdstip_registratie{}   # "" List Attribute
- LIST_ATTR_7 = bgt-status{}   # "" List Attribute
- LIST_ATTR_8 = lv-publicatiedatum{}   # "" List Attribute
- LIST_ATTR_9 = relatieve_hoogteligging{}   # "" List Attribute

Note: Er zitten in de GML lijsten bij een aantal generieke attributen. Dit lijkt onterecht. Daarom worden ze hier 'ge-explodeerd'
List_bgt_status_Input (input)
    -> ListExploder_bgt_status
List_tijdstip_registratie_Elements (output)

Bookmark: Generieke_attributen
Note: ListExploder_bgt_status
ListExploder_bgt_status
    LIST_ATTR = $(LIST_ATTR_7)
    ATTR_CONFLICT_RES = Use Incoming List
    ATTR_ACCUM_MODE = Merge Incoming List
    INDEX_ATTR = _element_index
    ELEMENTS -> ListExploder_eindregistratie
    <REJECTED> -> ListExploder_eindregistratie
Note: ListExploder_eindregistratie
ListExploder_eindregistratie
    LIST_ATTR = $(LIST_ATTR)
    ATTR_CONFLICT_RES = Use Incoming List
    ATTR_ACCUM_MODE = Merge Incoming List
    INDEX_ATTR = _element_index
    ELEMENTS -> ListExploder_bronhouder
    <REJECTED> -> ListExploder_bronhouder
Note: ListExploder_bronhouder
ListExploder_bronhouder
    LIST_ATTR = $(LIST_ATTR_4)
    ATTR_CONFLICT_RES = Use Incoming List
    ATTR_ACCUM_MODE = Merge Incoming List
    INDEX_ATTR = _element_index
    ELEMENTS -> ListExploder_imgeo_identificatie
    <REJECTED> -> ListExploder_imgeo_identificatie
Note: ListExploder_imgeo_identificatie
ListExploder_imgeo_identificatie
    LIST_ATTR = $(LIST_ATTR_3)
    ATTR_CONFLICT_RES = Use Incoming List
    ATTR_ACCUM_MODE = Merge Incoming List
    INDEX_ATTR = _element_index
    ELEMENTS -> ListExploder_in_onderzoek
    <REJECTED> -> ListExploder_in_onderzoek
Note: ListExploder_in_onderzoek
ListExploder_in_onderzoek
    LIST_ATTR = $(LIST_ATTR_5)
    ATTR_CONFLICT_RES = Use Incoming List
    ATTR_ACCUM_MODE = Merge Incoming List
    INDEX_ATTR = _element_index
    ELEMENTS -> ListExploder_lv_publ_datum
    <REJECTED> -> ListExploder_lv_publ_datum
Note: ListExploder_lv_publ_datum
ListExploder_lv_publ_datum
    LIST_ATTR = $(LIST_ATTR_8)
    ATTR_CONFLICT_RES = Use Incoming List
    ATTR_ACCUM_MODE = Merge Incoming List
    INDEX_ATTR = _element_index
    ELEMENTS -> ListExploder_plus_status
    <REJECTED> -> ListExploder_plus_status
Note: ListExploder_plus_status
ListExploder_plus_status
    LIST_ATTR = $(LIST_ATTR_2)
    ATTR_CONFLICT_RES = Use Incoming List
    ATTR_ACCUM_MODE = Merge Incoming List
    INDEX_ATTR = _element_index
    ELEMENTS -> ListExploder_relatieve_hoogteligging
    <REJECTED> -> ListExploder_relatieve_hoogteligging
Note: ListExploder_relatieve_hoogteligging
ListExploder_relatieve_hoogteligging
    LIST_ATTR = $(LIST_ATTR_9)
    ATTR_CONFLICT_RES = Use Incoming List
    ATTR_ACCUM_MODE = Merge Incoming List
    INDEX_ATTR = _element_index
    ELEMENTS -> ListExploder_tijdstip_registratie
    <REJECTED> -> ListExploder_tijdstip_registratie
Note: ListExploder_tijdstip_registratie
ListExploder_tijdstip_registratie
    LIST_ATTR = $(LIST_ATTR_6)
    ATTR_CONFLICT_RES = Use Incoming List
    ATTR_ACCUM_MODE = Merge Incoming List
    INDEX_ATTR = _element_index
    ELEMENTS -> List_tijdstip_registratie_Elements (output)
    <REJECTED> -> List_tijdstip_registratie_Elements (output)

FME custom transformer Huisnummerlabeler

Parameters:
- OBJECTEINDTIJD = @Value(objecteindtijd)   # objecteindtijd
- IMGEO_NUMMERAANDUIDINGREEKS_IMGEO_NUMMERAANDUIDINGREEKS = @Value(imgeo_nummeraanduidingreeks_imgeo_nummeraanduidingreeks)   # imgeo_nummeraanduidingreeks_imgeo_nummeraanduidingreeks
- IMGEO_NUMMERAANDUIDINGREEKS_IMGEO_IDENTIFICATIE_BAGVBOLAAGSTE_HUISNUMMER = @Value(imgeo_nummeraanduidingreeks_imgeo_identificatie_bagvbolaagste_huisnummer)   # Imgeo Nummeraanduidingreeks Imgeo Identificatie Bagvbolaagste Huisnummer
- IMGEO_NUMMERAANDUIDINGREEKS_IMGEO_IDENTIFICATIE_BAGVBOHOOGSTE_HUISNUMMER = @Value(imgeo_nummeraanduidingreeks_imgeo_identificatie_bagvbohoogste_huisnummer)   # Imgeo Nummeraanduidingreeks Imgeo Identificatie Bagvbohoogste Huisnummer
- _NUM_INDEX = @Value(_num_index)   # Num Index
- OBJECTBEGINTIJD = @Value(objectbegintijd)   # objectbegintijd
- GML_ID = @Value(gml_id)   # Gml Id

XMLFlattener_numreeks_Input (input)
    -> XMLFlattener_numreeks
Note: XMLFlattener_numreeks
XMLFlattener_numreeks
    NEW_ATTRIBUTES = Label.tekst Label.positie.Labelpositie.plaatsingspunt.Point.pos Label.positie.Labelpositie.hoek
    XML_SOURCE_TYPE = Attribute with XML document
    EMBEDDED_EXPRESSIONS = imgeo:nummeraanduidingreeks
    FLATTEN_OPTIONS:
      <structure
      separator="."
      open-list-brace="{"
      close-list-brace="}"
      map-empty-elements="yes"
      matched-prefix="attributes"
      matched-attributes="yes"
      matched-ancestor-attributes=""
      cardinality="+{?}"
      except=""
      structure-prefix=""
      child-position-attribute=""
      attribute-identifier=""/>

      <!--
      The options here allows customization of the attributes and attribute lists of the matched XML subtree
      that will be added to FME Features.

      Here are the following options that can be specified:

      1. separator
      This value of this option is used as the separator in the naming of the attributes of the children of the matched elements.

      Default value: .
      Possible values: any string

      2. open-list-brace
      Specifies the open list index delimiter brace for the flattened attributes.

      Default value: {
      Possible values: any string

      3. close-list-brace
      Specifies the close list index delimiter brace for the flattened attributes.

      Default value: }
      Possible values: any string

      4. map-empty-elements
      If set to yes, then any empty elements will be added as attributes with empty values onto the features.
      Otherwise, the attributes will not be added onto the features.

      Default value if not specified: yes
      Possible values: yes|no

      Default value:
      Possible values: any string

      5. matched-prefix
      This option controls whether FME feature attributes produced will be prefixed with matched element's name.
      If the value is 'yes', then both the matched element's attributes and all its children are prefixed
      If the value is 'no', then none of the feature attributes are prefixed with matched element's name
      If the value is 'children', then only the children of the matched element are prefixed
      If the value is 'attributes', then only the attributes of the matched element are prefixed

      Default value if not specified: yes
      Possible values: yes|no|children|attributes

      6. matched-attributes
      If this option is set to 'yes' then the attributes of the matched element are mapped as FME feature attributes.
      Otherwise, the attributes of the matched element are ignored.

      matched-prefix option can also be set to 'attributes' or 'yes' to allow the attributes to be prefixed with
      the name of the matched element.

      Default value if not specified: yes
      Possible values: yes|no

      7. matched-ancestor-attributes
      The option controls whether XML attributes from ancestor of the matched element should be included as FME feature attributes.

      The valid values for this option are:
      - 'parent' or '1'         : XML attributes of the parent of the matched element are added
      - 'grandparent' or '2'    : XML attributes of the grandparent of the matched element are added
      - 'root' or '-1'          : XML attributes of the root of the document are added
      - any non-negative number : XML attributes of the ancestor by going up x levels from the matched element are added.
                                  0 is the matched element.

      To include more than one ancestor, multiple values can be separated by a space.
      For example: To get the attributes from root, parent and grand parent, we can specify
      matched-ancestor-attributes="parent grandparent root"

      Default value:
      Possible values: parent|grandparent|root

      8. cardinality
      This option can be specified as a space separated list of cardinality directives.

      Default value: +{?} (Treat child elements as a list if there are more than one with the same name)
      Possible values: Refer to the documentation of XFMap section in XML Reader documentation

      9. structure-prefix
      This option can be set to non-empty string that serves as a prefix to every attribute that is generated for a matched element.

      Default value:
      Possible values: any string

      10. except
      The except attribute accepts the same types of expressions as the match or except attribute of a mapping rule.
      For example, the expression except=”parent/child{2}” could be used to exclude the second <child> element
      contained in a <parent> element from the output of the structure subrule.

      Default value:
      Possible values: any path expression

      11. child-position-attribute
      When this option is set to non-empty string, each child element will generate an additional feature attribute
      whose value will be the position of the child element witihin its parent.

      Default value:
      Possible values: any string

      12. attribute-identifier (Any string)
      XML attributes can be differentiated from leaf elements. By setting this option to non-empty string, XML reader
      will append a prefix to the attributes in the leaf elements.

      All the options have more elaborated examples and descriptions in the XML reader documentation.
      -->
    ATTRIBUTE_XML = imgeo_nummeraanduidingreeks_imgeo_nummeraanduidingreeks
    FEATURE_TYPES_FORMAT_NAME = XML
    -> AttributeCopier
AttributeCopier
    ATTR_TABLE = COPY Label.positie.Labelpositie.plaatsingspunt.Point.pos > label_wkt = @Value(Label.positie.Labelpositie.plaatsingspunt.Point.pos)
    -> StringReplacer_wkt_start
StringReplacer_wkt_start
    REPLACE_TEXT = POINT (
    REGEXP = YES
    NO_MATCH = _FME_NO_OP_
    FIND_TEXT = ^
    CASE = NO
    SRC_ATTRS = label_wkt
    -> StringReplacer_wkt_eind
StringReplacer_wkt_eind
    REPLACE_TEXT = )
    REGEXP = YES
    NO_MATCH = _FME_NO_OP_
    FIND_TEXT = $
    CASE = NO
    SRC_ATTRS = label_wkt
    -> AttributeManager
AttributeManager
    ATTR_TABLE:
      RENAME_SET_VALUE Label.tekst > tekst_huisnummerReeks
      RENAME_SET_VALUE Label.positie.Labelpositie.plaatsingspunt.Point.pos > plaatingspunt_hnr
      RENAME_SET_VALUE Label.positie.Labelpositie.hoek > hoek_hnr
    -> GeometryReplacer
Note: Verwijder_overbodige_attributen
GeometryReplacer
    SOURCE = @Value(label_wkt)
    OGC_WKT_PRECISION_DISPLAY = 64-bit
    KIND_LONG = OGC Well Known Text
    REMOVE_ATTRIBUTE = No
    -> GeometryReplacer_Output (output)
GeometryReplacer_Output (output)

FME custom transformer OpenbareRuimteLabelExtractor

Parameters:
- IMGEO_OPENBARE_RUIMTE_NAAM = @Value(imgeo_openbare_ruimte_naam)   # Imgeo Openbare Ruimte Naam

XMLXQueryExploder_labelpositiecompound_Input (input)
    -> XMLXQueryExploder_labelpositiecompound
Note: XMLXQueryExploder_positie
XMLXQueryExploder_labelpositiecompound
    QUERY_EXPR:
      declare namespace gml="http://www.opengis.net/gml";
      declare namespace imgeo="http://www.geostandaarden.nl/imgeo/2.1";
      //imgeo:Labelpositie
    XQUERY_TYPE = XQuery expression
    RESULT_ATTRIBUTE = _xq_compound_positie
    XML_TYPE = Attribute specifying XML
    TAG_ATTR = _source_compound_positie
    WRITE_XML_HEADER = No
    XML_REMOVE_SOURCE_ATTR = No
    XML_ATTR = imgeo_openbare_ruimte_naam
    QUERY_RESULTS -> XMLXQueryExtractor_opr_naam
    INVALID -> XMLXQueryExploder_labelpositiecompound_Invalid
Note: XMLXQueryExtractor_opr_naam
XMLXQueryExtractor_opr_naam
    RESULT_ATTRIBUTE = _opr_labeltekst
    QUERY_EXPR:
      declare namespace imgeo="http://www.geostandaarden.nl/imgeo/2.1";
      declare namespace gml="http://www.opengis.net/gml";
      //imgeo:tekst
    XML_ATTR = imgeo_openbare_ruimte_naam
    XQUERY_TYPE = XQuery expression
    XML_TYPE = Attribute specifying XML
    RESULT_TYPE_NAME = Single value
    XML_REMOVE_SOURCE_ATTR = No
    WRITE_XML_HEADER = No
    QUERY_RESULTS -> XMLXQueryExtractor_opr_labelpos
Note: XMLXQueryExtractor_opr_labelpos
XMLXQueryExtractor_opr_labelpos
    RESULT_ATTRIBUTE = _opr_labelpos
    QUERY_EXPR:
      declare namespace imgeo="http://www.geostandaarden.nl/imgeo/2.1";
      declare namespace gml="http://www.opengis.net/gml";
      //gml:pos
    XML_ATTR = _xq_compound_positie
    XQUERY_TYPE = XQuery expression
    XML_TYPE = Attribute specifying XML
    RESULT_TYPE_NAME = Single value
    XML_REMOVE_SOURCE_ATTR = No
    WRITE_XML_HEADER = No
    QUERY_RESULTS -> XMLXQueryExtractor_opr_labelhoek
    INVALID -> XMLXQueryExtractor_opr_labelpos_Invalid
Note: XMLXQueryExtractor_opr_labelhoek
XMLXQueryExtractor_opr_labelhoek
    RESULT_ATTRIBUTE = _opr_labelhoek
    QUERY_EXPR:
      declare namespace imgeo="http://www.geostandaarden.nl/imgeo/2.1";
      declare namespace gml="http://www.opengis.net/gml";
      //imgeo:hoek
    XML_ATTR = _xq_compound_positie
    XQUERY_TYPE = XQuery expression
    XML_TYPE = Attribute specifying XML
    RESULT_TYPE_NAME = Single value
    XML_REMOVE_SOURCE_ATTR = No
    WRITE_XML_HEADER = No
    QUERY_RESULTS -> XMLFlattener_labelpos
Note: XMLFlattener_labelpos
XMLFlattener_labelpos
    NEW_ATTRIBUTES = pos
    XML_SOURCE_TYPE = Attribute with XML document
    EMBEDDED_EXPRESSIONS = gml:pos
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _opr_labelpos
    FEATURE_TYPES_FORMAT_NAME = XML
    -> XMLFlattener_labelhoek
Note: XMLFlattener_labelhoek
XMLFlattener_labelhoek
    NEW_ATTRIBUTES = hoek
    XML_SOURCE_TYPE = Attribute with XML document
    EMBEDDED_EXPRESSIONS = imgeo:hoek
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _opr_labelhoek
    FEATURE_TYPES_FORMAT_NAME = XML
    -> XMLFlattener_labeltekst
Note: XMLFlattener_labeltekst
XMLFlattener_labeltekst
    NEW_ATTRIBUTES = tekst
    XML_SOURCE_TYPE = Attribute with XML document
    EMBEDDED_EXPRESSIONS = imgeo:tekst
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _opr_labeltekst
    FEATURE_TYPES_FORMAT_NAME = XML
    -> AttributeRenamer
Note: AttributeRenamer
AttributeRenamer
    ATTR_TABLE:
      RENAME_SET_DEFAULT tekst > opr_label_tekst
      RENAME_SET_DEFAULT hoek > opr_label_hoek
    -> AttributeCopier_pos
AttributeCopier_pos
    ATTR_TABLE = COPY pos > opr_labelpos = @Evaluate(@Value(pos))
    -> StringReplacer_opr_pos
StringReplacer_opr_pos
    REPLACE_TEXT = POINT (
    REGEXP = YES
    NO_MATCH = _FME_NO_OP_
    FIND_TEXT = ^
    CASE = NO
    SRC_ATTRS = opr_labelpos
    -> StringReplacer_opr_eind
StringReplacer_opr_eind
    REPLACE_TEXT = )
    REGEXP = YES
    NO_MATCH = _FME_NO_OP_
    FIND_TEXT = $
    CASE = NO
    SRC_ATTRS = opr_labelpos
    -> GeometryReplacer_labelpos
GeometryReplacer_labelpos
    SOURCE = @Value(opr_labelpos)
    OGC_WKT_PRECISION_DISPLAY = 64-bit
    KIND_LONG = OGC Well Known Text
    REMOVE_ATTRIBUTE = No
    -> GeometryReplacer_labelpos_Output (output)
    <REJECTED> -> GeometryReplacer_labelpos__Rejected_
GeometryReplacer_labelpos_Output (output)
GeometryReplacer_labelpos__Rejected_: Inspector
XMLXQueryExtractor_opr_labelpos_Invalid: Inspector
XMLXQueryExploder_labelpositiecompound_Invalid: Inspector
