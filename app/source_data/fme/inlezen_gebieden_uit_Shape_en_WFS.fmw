FME workspace inlezen_gebieden_uit_Shape_en_WFS.fmw

Parameters:
- SourceDataset_WFS_5 = https://map.data.amsterdam.nl/maps/gebieden?REQUEST=GetCapabilities&SERVICE=wfs   # Source WFS (Web Feature Service) URL
- DestDataset_ESRISHAPE = C:\Users\riemen002\OneDrive - Gemeente Amsterdam\Documenten\GOB\BGT\BGT\kaartbladindeling   # Destination Esri Shapefile Folder
- DestDataset_DGNV8 = C:\Users\riemen002\OneDrive - Gemeente Amsterdam\Documenten\GOB\BGT\BGT\kaartbladindeling\PDOK_Indeling.dgn   # Destination Bentley MicroStation Design File
- DestDataset_POSTGIS_4 = bgt_local   # Connection
- SourceDataset_Gemeentes = C:\Users\riemen002\OneDrive - Gemeente Amsterdam\Documenten\GOB\BGT\BGT\app\source_data\bron_csv\gemeentes.csv   # Source CSV (Comma Separated Value) File(s)
- P_SEED = C:\Users\riemen002\OneDrive - Gemeente Amsterdam\Documenten\GOB\BGT\BGT\app\source_data\aanmaak_producten_bgt\resource\DGNv8_seed.dgn   # Seed File (V8only)
- P_CEL = C:\Users\riemen002\OneDrive - Gemeente Amsterdam\Documenten\GOB\BGT\BGT\app\source_data\aanmaak_producten_bgt\resource\NLCS.cel   # Cell Library File
- SourceDataset_Kaartbladen = C:\Users\riemen002\OneDrive - Gemeente Amsterdam\Documenten\GOB\BGT\BGT\app\source_data\bron_csv\bgt_kaartbladen.csv   # Source CSV (Comma Separated Value) File(s)
- SourceDataset_WKT = C:\Users\riemen002\OneDrive - Gemeente Amsterdam\Documenten\GOB\BGT\BGT\app\source_data\bron_csv\oude_polygoon_bgt.csv   # Source Text File(s)
- SourceDataset_WFS_4 = https://service.pdok.nl/kadaster/bestuurlijkegebieden/wfs/v1_0?request=GetCapabilities&service=WFS   # Source WFS (Web Feature Service) URL

Readers:
- WFS_2: WFS from $(SourceDataset_WFS_5)
- CSV2_1: CSV2 from $(SourceDataset_Gemeentes)
- CSV2_2: CSV2 from $(SourceDataset_Kaartbladen)
- WKT_1: WKT from $(SourceDataset_WKT) in EPSG:28992
- WFS_3: WFS from $(SourceDataset_WFS_4)

Writers:
- ESRISHAPE_1: ESRISHAPE to $(DestDataset_ESRISHAPE) in EPSG:28992
- DGNV8_1: DGNV8 to $(DestDataset_DGNV8)
- POSTGIS_1: POSTGIS to $(DestDataset_POSTGIS_4) in EPSG:28992
- ESRISHAPE_2: ESRISHAPE to $(DestDataset_ESRISHAPE)

Note: Gemeentegebied: PDOK [WFS}, heel Nederland
Gemeentegebied (reader WFS_3)
    attributes: gml_parent_id xml_buffer, gml_parent_property xml_buffer, gml_id xml_buffer, geom xml_geometry, identificatie xml_buffer, naam xml_buffer, code xml_buffer, ligtInProvincieCode xml_buffer, ligtInProvincieNaam xml_buffer
    -> AttributeManager_GME_2
Note: verwijder overbodigheden en rename attr
AttributeManager_GME_2
    ATTR_TABLE:
      SET_TO big_id = 2
      REMOVE gml_id
      REMOVE gml_parent_id
      REMOVE gml_parent_property
      REMOVE geom
      REMOVE identificatie
      RENAME_SET_VALUE naam > NAAM
      REMOVE ligtInProvincieCode
      REMOVE ligtInProvincieNaam
    -> StringReplacer_5
Note: leestekens in namen weghalen
StringReplacer_5
    CASE = NO
    FIND_TEXT = '
    NO_MATCH = _FME_NO_OP_
    REGEXP = NO
    SRC_ATTRS = NAAM
    -> StringReplacer
StringReplacer
    CASE = NO
    FIND_TEXT = " "
    NO_MATCH = _FME_NO_OP_
    REGEXP = NO
    REPLACE_TEXT = _
    SRC_ATTRS = NAAM
    -> StringReplacer_4
StringReplacer_4
    CASE = NO
    FIND_TEXT = -
    NO_MATCH = _FME_NO_OP_
    REGEXP = NO
    SRC_ATTRS = NAAM
    -> FeatureMerger [REQUESTOR] [off]
    -> SpatialFilter [Candidate]
Note: stadsdeel: gebieden [WFS]
stadsdeel (reader WFS_2)
    attributes: gml_parent_id xml_buffer, gml_parent_property xml_buffer, gml_id xml_buffer, msGeometry xml_geometry, id xml_buffer, code xml_buffer, naam xml_buffer, display xml_buffer, type xml_buffer, uri xml_buffer
    -> AttributeManager_2
Note: verwijder overbodigheden en hernoem met prefix
AttributeManager_2
    ATTR_TABLE:
      REMOVE gml_parent_id
      REMOVE gml_parent_property
      REMOVE gml_id
      REMOVE msGeometry
      REMOVE id
      REMOVE code
      SET_TO naam > NAAM = Amsterdam_@Value(naam)
      REMOVE display
      REMOVE type
      REMOVE uri
      SET_TO big_id = 2
    -> Tester_2
Note: voor nieuwwest een uizondering maken. vanwege liggend streepje
Tester_2
    BOOL_OP = OR
    COMPOSITE_TEST = 1
    TEST_CLAUSE = TEST @Value(naam) = Nieuw-West
    TEST_MODE = TEST
    PASSED -> AttributeManager
    FAILED -> StringReplacer_2
AttributeManager
    ATTR_TABLE = SET_TO NAAM = Amsterdam_Nieuwwest
    -> StringReplacer_2
Note: leestekens in namen weghalen
StringReplacer_2
    CASE = NO
    FIND_TEXT = " "
    NO_MATCH = _FME_NO_OP_
    REGEXP = NO
    REPLACE_TEXT = _
    SRC_ATTRS = NAAM
    -> StringReplacer_3
StringReplacer_3
    CASE = NO
    FIND_TEXT = -
    NO_MATCH = _FME_NO_OP_
    REGEXP = NO
    SRC_ATTRS = NAAM
    -> AttributeKeeper
Note: mogelijke geometrische verschillen verwijderen
AttributeKeeper
    KEEP_ATTRS = NAAM,big_id
    -> TopologyBuilder
Note: bgt_kaartbladen.csv, hulpbestand met kaartbladen in wkt van heel NL
CSV (reader CSV2_2)
    attributes: identificatie string, bladnaam string, geometrie string
    -> AttributeManager_kbd
Note: verwijder overbodige kenmerken en rename
AttributeManager_kbd
    ATTR_TABLE:
      SET_TO big_id = 1
      REMOVE identificatie
      RENAME_SET_VALUE bladnaam > Bladnaam
    -> GeometryReplacer
GeometryReplacer
    KIND_LONG = OGC Well Known Text
    OGC_WKT_PRECISION_DISPLAY = 64-bit
    REMOVE_ATTRIBUTE = Yes
    SOURCE = @Value(geometrie)
    -> SpatialFilter_2 [Candidate]
Note: oude_polygoon_bgt [WKT]
well_known_text (reader WKT_1)
    attributes: source_wkt buffer, source_line_number buffer
    -> SpatialFilter [Filter]
    -> SpatialFilter_2 [Filter]
Note: Filter (tijdelijk) op basis van de oude polygoon
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Tester_3
Note: haal amsterdam eruit, / die komt via de andere lijn
Tester_3
    BOOL_OP = OR
    TEST_CLAUSE = TEST @Value(NAAM) = Amsterdam
    TEST_MODE = Automatic
    FAILED -> TopologyBuilder
TopologyBuilder
    ALLOW_CYCLES = No
    BOUNDING_EDGES = All
    CLEAN_DATA = No
    DEAGGREGATE_INPUT = Yes
    MAX = 0
    OVERLAPPING_MODE = No
    PROP_ATTRS = No
    AREA -> BGT_Gebiedsindeling (writer ESRISHAPE_1)
    AREA -> pdt_kaartblad (writer POSTGIS_1)
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> CenterPointReplacer_2
    PASSED -> pdt_kaartblad (writer POSTGIS_1)
    PASSED -> Kaartbladen (writer DGNV8_1)
CenterPointReplacer_2
    MODE = Center Point
    POINT -> LabelPointReplacer_3
LabelPointReplacer_3
    ALWAYSROTATE = yes
    HEIGHT = 10
    LABATTR = @Value(Bladnaam)
    LabelPoint -> Bladnummers (writer DGNV8_1)

Bookmark: UItselecteren van gemeenten - dit moet de definitieve oplossing worden, nu tijdelijk kleiner gemaakt
Note: gemeentes.csv; hulpbestand met de te leveren gemeentes
CSV (reader CSV2_1) [off]
    attributes: GME_ID string
    -> FeatureMerger [SUPPLIER] [off]
FeatureMerger [off]
    ATTR_ACCUM_MODE = Merge Supplier
    ATTR_CONFLICT_RES = Use Requestor
    IGNORE_NULLS = No
    JOIN_KEYS = @Value(code) @Value(GME_ID) AUTO
    MERGE_TYPE = Attributes Only
    PROCESS_DUPS = NO
    REJECT_NULL_MISSING_KEYS = No
    SUPPLIERS_FIRST = No
    MERGED -> Dissolver_2 [off]
    MERGED -> Tester_3 [off]
Dissolver_2 [off]
    ACCUM_INPUT_ATTRS = Use Attributes From One Feature
    CLEANING_TOLERANCE = Automatic
    CONNECT_Z_MODE = First Wins
    DEAGGREGATE_INPUT = Yes
    AREA -> polygoon_39_gemeenten (writer ESRISHAPE_2) [off]
    AREA -> SpatialFilter_2 [Filter] [off]
Note: Ter referentie, het hele levergebied in 1 polygoon
polygoon_39_gemeenten (writer ESRISHAPE_2) [off]

Bookmark: Shape
BGT_Gebiedsindeling (writer ESRISHAPE_1)
    attributes: naam char(200)

Bookmark: Postgres
pdt_kaartblad (writer POSTGIS_1)
    attributes: naam varchar(200), big_id int4

Bookmark: dgn
Kaartbladen (writer DGNV8_1)
Bladnummers (writer DGNV8_1)
